/**
 * Desc: DayII
 * Date: 2021
 * Author: WANGYizhi
 */
 
BSM DEFINITIONS AUTOMATIC TAGS ::= BEGIN

-- imports and exports

EXPORTS BasicSafetyMessage;
IMPORTS AccelerationSet4Way FROM DefAcceleration
		BrakeSystemStatus FROM VehBrake
		VehicleSize FROM VehSize
		Position3D, PositionConfidenceSet, PositionalAccuracy FROM DefPosition
		DSecond, TimeConfidence FROM DefTime
		TransmissionState FROM VehStatus
		Speed, Heading, SteeringWheelAngle, MotionConfidenceSet FROM DefMotion
		MsgCount FROM MsgFrame
		VehicleClassification FROM VehClass
		VehicleSafetyExtensions FROM VehSafetyExt
		VehicleEmergencyExtensions FROM VehEmgExt;
	
	BasicSafetyMessage ::= SEQUENCE {
		msgCnt MsgCount,
		id OCTET STRING (SIZE(8)),
		-- temperary vehicle ID
		secMark DSecond,
		timeConfidence TimeConfidence OPTIONAL,
		pos Position3D,
		posAccuracy PositionalAccuracy OPTIONAL,
		-- Accuracy for GNSS system
		posConfidence PositionConfidenceSet OPTIONAL,
		-- Realtime position confidence
		transmission TransmissionState,
		speed Speed,
		heading Heading,
		angle SteeringWheelAngle OPTIONAL,
		motionCfd MotionConfidenceSet OPTIONAL,
		accelSet AccelerationSet4Way,
		brakes BrakeSystemStatus,
		size VehicleSize,
		vehicleClass VehicleClassification,
		-- VehicleClassification includes BasicVehicleClass and other extendible type
		safetyExt VehicleSafetyExtensions OPTIONAL,
		emergencyExt VehicleEmergencyExtensions OPTIONAL,
		...
	}
	
END

DefAcceleration DEFINITIONS AUTOMATIC TAGS ::= BEGIN

-- imports and exports

EXPORTS AccelerationSet4Way, YawRate;
IMPORTS ;
	
	AccelerationSet4Way ::= SEQUENCE {
		long Acceleration, 
		-- Along the Vehicle Longitudinal axis
		lat Acceleration, 
		-- Along the Vehicle Lateral axis
		vert VerticalAcceleration, 
		-- Along the Vehicle Vertical axis
		yaw YawRate
	}
	
	Acceleration ::= INTEGER (-2000..2001)
	-- Units are 0.01 m/s^2 
	-- the value 2000 shall be used for values greater than 2000 
	-- the value -2000 shall be used for values less than -2000 
	-- a value of 2001 shall be used for Unavailable
	
	VerticalAcceleration ::= INTEGER (-127..127)
	-- Units of 0.02 G steps over -2.52 to +2.54 G
	-- The value +127 shall be used for ranges >= 2.54 G
	-- The value -126 shall be used for ranges <= 2.52 G
	-- The value -127 shall be used for unavailable
	
	YawRate ::= INTEGER (-32767..32767)
	-- Units of 0.01 degrees per second (signed)
	
END

DefMotion DEFINITIONS AUTOMATIC TAGS ::= BEGIN

-- imports and exports

EXPORTS Speed, Heading, SteeringWheelAngle, SpeedConfidence, MotionConfidenceSet, CoarseHeading, HeadingConfidence;
IMPORTS ;
	
	Speed ::= INTEGER (0..8191)
	-- Units of 0.02 m/s
	-- The value 8191 indicates that
	-- speed is unavailable
	
	Heading ::= INTEGER (0..28800) 
	-- Units of 0.0125 degrees 
	-- A range of 0 to 359.9875 degrees
	
	CoarseHeading ::= INTEGER (0..240)
	-- Units of 1.5 degrees
	-- over a range of 0~358.5 degrees
	-- the value 240 shall be used for unavailable
	
	SteeringWheelAngle ::= INTEGER (-126..127)
	-- Units of 1.5 degrees, a range of -189 to +189 degrees
	-- +001 = +1.5 deg
	-- -126 = -189 deg and beyond
	-- +126 = +189 deg and beyond
	-- +127 to be used for unavailable
	
	MotionConfidenceSet ::= SEQUENCE {
		speedCfd SpeedConfidence OPTIONAL,
		headingCfd HeadingConfidence OPTIONAL,
		steerCfd SteeringWheelAngleConfidence OPTIONAL
	}
	
	HeadingConfidence ::= ENUMERATED {
		unavailable (0), -- Not Equipped or unavailable
		prec10deg (1), -- 10 degrees
		prec05deg (2), -- 5 degrees
		prec01deg (3), -- 1 degrees
		prec0-1deg (4), -- 0.1 degrees
		prec0-05deg (5), -- 0.05 degrees
		prec0-01deg (6), -- 0.01 degrees
		prec0-0125deg (7) -- 0.0125 degrees, aligned with heading LSB
		}
	
	SpeedConfidence ::= ENUMERATED {
		unavailable (0), -- Not Equipped or unavailable
		prec100ms (1), -- 100 meters / sec
		prec10ms (2), -- 10 meters / sec
		prec5ms (3), -- 5 meters / sec
		prec1ms (4), -- 1 meters / sec
		prec0-1ms (5), -- 0.1 meters / sec
		prec0-05ms (6), -- 0.05 meters / sec
		prec0-01ms (7) -- 0.01 meters / sec
		}
	
	SteeringWheelAngleConfidence ::= ENUMERATED {
		unavailable (0), -- Not Equipped with Wheel angle
		-- or Wheel angle status is unavailable
		prec2deg (1), -- 2 degrees
		prec1deg (2), -- 1 degree
		prec0-02deg (3) -- 0.02 degrees
		}
	
	
END

DefPosition DEFINITIONS AUTOMATIC TAGS ::= BEGIN

-- imports and exports

EXPORTS Latitude, Longitude, Elevation, PositionConfidenceSet, Position3D, PositionalAccuracy;
IMPORTS ;
	
	Latitude ::= INTEGER (-900000000..900000001) 
	-- Units of 1/10 micro degree 
	-- Providing a range of plus-minus 90 degrees
	
	Longitude ::= INTEGER (-1799999999..1800000001) 
	-- Units of 1/10 micro degree 
	-- Providing a range of plus-minus 180 degrees
	
	Elevation ::= INTEGER (-4096..61439)
	-- Units of 10 cm steps above or below the reference ellipsoid
	-- Providing a range of -409.5 to + 6143.9 meters
	-- The value -4096 shall be used when Unknown is to be sent
	
	PositionConfidenceSet ::= SEQUENCE {
		pos PositionConfidence, -- for both horizontal directions
		elevation ElevationConfidence OPTIONAL
	}
	
	PositionConfidence ::= ENUMERATED {
		unavailable (0), -- Not Equipped or unavailable
		a500m (1), -- 500m or about 5 * 10 ^ -3 decimal degrees
		a200m (2), -- 200m or about 2 * 10 ^ -3 decimal degrees
		a100m (3), -- 100m or about 1 * 10 ^ -3 decimal degrees
		a50m (4), -- 50m or about 5 * 10 ^ -4 decimal degrees
		a20m (5), -- 20m or about 2 * 10 ^ -4 decimal degrees
		a10m (6), -- 10m or about 1 * 10 ^ -4 decimal degrees
		a5m (7), -- 5m or about 5 * 10 ^ -5 decimal degrees
		a2m (8), -- 2m or about 2 * 10 ^ -5 decimal degrees
		a1m (9), -- 1m or about 1 * 10 ^ -5 decimal degrees
		a50cm (10), -- 0.50m or about 5 * 10 ^ -6 decimal degrees
		a20cm (11), -- 0.20m or about 2 * 10 ^ -6 decimal degrees
		a10cm (12), -- 0.10m or about 1 * 10 ^ -6 decimal degrees
		a5cm (13), -- 0.05m or about 5 * 10 ^ -7 decimal degrees
		a2cm (14), -- 0.02m or about 2 * 10 ^ -7 decimal degrees
		a1cm (15) -- 0.01m or about 1 * 10 ^ -7 decimal degrees
	}
	
	ElevationConfidence ::= ENUMERATED {
		unavailable (0), -- Not Equipped or unavailable
		elev-500-00 (1), -- (500 m)
		elev-200-00 (2), -- (200 m)
		elev-100-00 (3), -- (100 m)
		elev-050-00 (4), -- (50 m)
		elev-020-00 (5), -- (20 m)
		elev-010-00 (6), -- (10 m)
		elev-005-00 (7), -- (5 m)
		elev-002-00 (8), -- B(2 m)
		elev-001-00 (9), -- (1 m)
		elev-000-50 (10), -- (50 cm)
		elev-000-20 (11), -- (20 cm)
		elev-000-10 (12), -- (10 cm)
		elev-000-05 (13), -- (5 cm)
		elev-000-02 (14), -- B(2 cm)
		elev-000-01 (15) -- (1 cm)
	}
	
	Position3D ::= SEQUENCE {
		lat Latitude, 
		-- in 1/10th micro degrees
		long Longitude, 
		-- in 1/10th micro degrees
		elevation Elevation OPTIONAL
		-- in 10 cm units
	}
	
	SemiMajorAxisAccuracy ::= INTEGER (0..255)
	-- semi-major axis accuracy at one standard dev
	-- range 0-12.7 meter, LSB = .05m
	-- 254 = any value equal or greater than 12.70 meter
	-- 255 = unavailable semi-major axis value
	
	SemiMinorAxisAccuracy ::= INTEGER (0..255)
	-- semi-minor axis accuracy at one standard dev
	-- range 0-12.7 meter, LSB = .05m
	-- 254 = any value equal or greater than 12.70 meter
	-- 255 = unavailable semi-minor axis value
	
	SemiMajorAxisOrientation ::= INTEGER (0..65535)
	-- orientation of semi-major axis
	-- relative to true north (0~359.9945078786 degrees)
	-- Units of 360/65535 deg = 0.0054932479
	-- a value of 0 shall be 0 degrees
	-- a value of 1 shall be 0.0054932479 degrees
	-- a value of 65534 shall be 359.9945078786 deg
	-- a value of 65535 shall be used for orientation unavailable
	
	PositionalAccuracy ::= SEQUENCE {
		-- NMEA-183 values expressed in strict ASN form
		semiMajor SemiMajorAxisAccuracy,
		semiMinor SemiMinorAxisAccuracy,
		orientation SemiMajorAxisOrientation
	}
END

DefPositionOffset DEFINITIONS AUTOMATIC TAGS ::= BEGIN

-- imports and exports

EXPORTS PositionOffsetLLV;
IMPORTS Longitude, Latitude, Elevation FROM DefPosition;
	
	PositionOffsetLLV ::= SEQUENCE {
		offsetLL PositionOffsetLL,
		-- offset in lon/lat
		offsetV VerticalOffset OPTIONAL
		-- offset in elevation
	}
	
	OffsetLL-B12 ::= INTEGER (-2048..2047) 
	-- A range of +- 0.0002047 degrees 
	-- Units of 0.1 microdegrees 
	OffsetLL-B14 ::= INTEGER (-8192..8191) 
	-- A range of +- 0.0008191 degrees 
	-- Units of 0.1 microdegrees
	OffsetLL-B16 ::= INTEGER (-32768..32767) 
	-- A range of +- 0.0032767 degrees 
	-- Units of 0.1 microdegrees
	OffsetLL-B18 ::= INTEGER (-131072..131071) 
	-- A range of +- 0.0131071 degrees 
	-- Units of 0.1 microdegrees
	OffsetLL-B22 ::= INTEGER (-2097152..2097151) 
	-- A range of +- 0.2097151 degrees 
	-- Units of 0.1 microdegrees
	OffsetLL-B24 ::= INTEGER (-8388608..8388607) 
	-- A range of +- 0.8388607 degrees 
	-- Units of 0.1 microdegrees
	
	Position-LL-24B ::= SEQUENCE { 
		-- ranges of +- 0.0002047 degrees 
		-- ranges of +- 22.634554 meters at the equator
		lon OffsetLL-B12,
		lat OffsetLL-B12
		}
	
	Position-LL-28B ::= SEQUENCE { 
		-- ranges of +- 0.0008191 degrees 
		-- ranges of +- 90.571389 meters at the equator
		lon OffsetLL-B14,
		lat OffsetLL-B14
		}
	
	Position-LL-32B ::= SEQUENCE { 
		-- ranges of +- 0.0032767 degrees 
		-- ranges of +- 362.31873 meters at the equator
		lon OffsetLL-B16,
		lat OffsetLL-B16
		}
	
	Position-LL-36B ::= SEQUENCE { 
		-- ranges of +- 0.0131071 degrees 
		-- ranges of +- 01.449308 Kmeters at the equator
		lon OffsetLL-B18,
		lat OffsetLL-B18
		}
	
	Position-LL-44B ::= SEQUENCE { 
		-- ranges of +- 0.2097151 degrees 
		-- ranges of +- 23.189096 Kmeters at the equator
		lon OffsetLL-B22,
		lat OffsetLL-B22
		}
	
	Position-LL-48B ::= SEQUENCE { 
		-- ranges of +- 0.8388607 degrees 
		-- ranges of +- 92.756481 Kmeters at the equator
		lon OffsetLL-B24,
		lat OffsetLL-B24
		}
	
	Position-LLmD-64b ::= SEQUENCE {
		-- a full 32b Lat/Lon range
		lon Longitude,
		lat Latitude
		}
	
	PositionOffsetLL ::= CHOICE { 
		-- Locations with LL content Span at the equator when using a zoom of one:
		position-LL1 Position-LL-24B, 
		-- within +- 22.634554 meters of the reference position
		position-LL2 Position-LL-28B, 
		-- within +- 90.571389 meters of the reference position
		position-LL3 Position-LL-32B, 
		-- within +- 362.31873 meters of the reference position
		position-LL4 Position-LL-36B, 
		-- within +- 01.449308 Kmeters of the reference position
		position-LL5 Position-LL-44B, 
		-- within +- 23.189096 Kmeters of the reference position
		position-LL6 Position-LL-48B, 
		-- within +- 92.756481 Kmeters of the reference position
		position-LatLon Position-LLmD-64b 
		-- node is a Lat/Lon absolute coordinates
		-- not a reference position
	}
	
	VerticalOffset ::= CHOICE { 
		-- Vertical Offset 
		-- All below in steps of 10cm above or below the reference ellipsoid
		offset1 VertOffset-B07, -- with a range of +- 6.3 meters vertical
		offset2 VertOffset-B08, -- with a range of +- 12.7 meters vertical
		offset3 VertOffset-B09, -- with a range of +- 25.5 meters vertical
		offset4 VertOffset-B10, -- with a range of +- 51.1 meters vertical
		offset5 VertOffset-B11, -- with a range of +- 102.3 meters vertical
		offset6 VertOffset-B12, -- with a range of +- 204.7 meters vertical
		elevation Elevation -- with a range of -409.5 to + 6143.9 meters
		}
	
	VertOffset-B07 ::= INTEGER (-64..63) 
	-- Units of of 10 cm 
	-- with a range of +- 6.3 meters vertical 
	-- value 63 to be used for 63 or greater 
	-- value -63 to be used for -63 or greater 
	-- value -64 to be unavailable
	
	VertOffset-B08 ::= INTEGER (-128..127) 
	-- Units of of 10 cm 
	-- with a range of +- 12.7 meters vertical 
	-- value 127 to be used for 127 or greater 
	-- value -127 to be used for -127 or greater 
	-- value -128 to be unavailable
	
	VertOffset-B09 ::= INTEGER (-256..255) 
	-- Units of of 10 cm 
	-- with a range of +- 25.5 meters vertical 
	-- value 255 to be used for 255 or greater 
	-- value -255 to be used for -255 or greater 
	-- value -256 to be unavailable
	
	VertOffset-B10 ::= INTEGER (-512..511) 
	-- Units of of 10 cm 
	-- with a range of +- 51.1 meters vertical 
	-- value 511 to be used for 511 or greater 
	-- value -511 to be used for -511 or greater 
	-- value -512 to be unavailable
	
	VertOffset-B11 ::= INTEGER (-1024..1023) 
	-- Units of of 10 cm 
	-- with a range of +- 102.3 meters vertical 
	-- value 1023 to be used for 1023 or greater 
	-- value -1023 to be used for -1023 or greater 
	-- value -1024 to be unavailable
	
	VertOffset-B12 ::= INTEGER (-2048..2047) 
	-- Units of of 10 cm 
	-- with a range of +- 204.7 meters vertical 
	-- value 2047 to be used for 2047 or greater 
	-- value -2047 to be used for -2047 or greater 
	-- value -2048 to be unavailable
	
END

DefTime DEFINITIONS AUTOMATIC TAGS ::= BEGIN

-- imports and exports

EXPORTS DSecond, MinuteOfTheYear, TimeMark, TimeOffset, TimeConfidence, DDateTime, DYear, DMonth, DDay;
IMPORTS ;
		
	DSecond ::= INTEGER (0..65535)
	-- units of milliseconds
	
	DYear ::= INTEGER (0..4095) 
	-- units of years
	
	DMonth ::= INTEGER (0..12) 
	-- units of months
	
	DDay ::= INTEGER (0..31) 
	-- units of days
	
	DHour ::= INTEGER (0..31) 
	-- units of hours
	
	DMinute ::= INTEGER (0..60) 
	-- units of minutes
	
	DTimeOffset ::= INTEGER (-840..840) 
	-- units of minutes from UTC time
	
	DDateTime ::= SEQUENCE {
		year DYear OPTIONAL,
		month DMonth OPTIONAL,
		day DDay OPTIONAL,
		hour DHour OPTIONAL,
		minute DMinute OPTIONAL,
		second DSecond OPTIONAL,
		offset DTimeOffset OPTIONAL -- time zone
		}
	
	MinuteOfTheYear ::= INTEGER (0..527040) 
	-- the value 527040 shall be used for invalid
	
	TimeMark ::= INTEGER (0..36001) 
	-- Tenths of a second in the current or next hour 
	-- In units of 1/10th second from UTC time 
	-- A range of 0~36000 covers one hour 
	-- The values 35991..35999 are used when a leap second occurs 
	-- The value 36000 is used to indicate time >3600 seconds 
	-- 36001 is to be used when value undefined or unknown 
	-- Note that this is NOT expressed in GNSS time 
	-- or in local time
	
	TimeOffset ::= INTEGER (1..65535) 
	-- Units of of 10 mSec, 
	-- with a range of 0.01 seconds to 10 minutes and 55.34 seconds 
	-- a value of 65534 to be used for 655.34 seconds or greater 
	-- a value of 65535 to be unavailable
	
	TimeConfidence ::= ENUMERATED {
		unavailable (0), -- Not Equipped or unavailable
		time-100-000 (1), -- Better than 100 Seconds
		time-050-000 (2), -- Better than 50 Seconds
		time-020-000 (3), -- Better than 20 Seconds
		time-010-000 (4), -- Better than 10 Seconds
		time-002-000 (5), -- Better than 2 Seconds
		time-001-000 (6), -- Better than 1 Second
		time-000-500 (7), -- Better than 0.5 Seconds
		time-000-200 (8), -- Better than 0.2 Seconds
		time-000-100 (9), -- Better than 0.1 Seconds
		time-000-050 (10), -- Better than 0.05 Seconds
		time-000-020 (11), -- Better than 0.02 Seconds
		time-000-010 (12), -- Better than 0.01 Seconds
		time-000-005 (13), -- Better than 0.005 Seconds
		time-000-002 (14), -- Better than 0.002 Seconds
		time-000-001 (15), -- Better than 0.001 Seconds
		-- Better than one millisecond
		time-000-000-5 (16), -- Better than 0.000,5 Seconds
		time-000-000-2 (17), -- Better than 0.000,2 Seconds
		time-000-000-1 (18), -- Better than 0.000,1 Seconds
		time-000-000-05 (19), -- Better than 0.000,05 Seconds
		time-000-000-02 (20), -- Better than 0.000,02 Seconds
		time-000-000-01 (21), -- Better than 0.000,01 Seconds
		time-000-000-005 (22), -- Better than 0.000,005 Seconds
		time-000-000-002 (23), -- Better than 0.000,002 Seconds
		time-000-000-001 (24), -- Better than 0.000,001 Seconds
		-- Better than one micro second
		time-000-000-000-5 (25), -- Better than 0.000,000,5 Seconds
		time-000-000-000-2 (26), -- Better than 0.000,000,2 Seconds
		time-000-000-000-1 (27), -- Better than 0.000,000,1 Seconds
		time-000-000-000-05 (28), -- Better than 0.000,000,05 Seconds
		time-000-000-000-02 (29), -- Better than 0.000,000,02 Seconds
		time-000-000-000-01 (30), -- Better than 0.000,000,01 Seconds
		time-000-000-000-005 (31), -- Better than 0.000,000,005 Seconds
		time-000-000-000-002 (32), -- Better than 0.000,000,002 Seconds
		time-000-000-000-001 (33), -- Better than 0.000,000,001 Seconds
		-- Better than one nano second
		time-000-000-000-000-5 (34), -- Better than 0.000,000,000,5 Seconds
		time-000-000-000-000-2 (35), -- Better than 0.000,000,000,2 Seconds
		time-000-000-000-000-1 (36), -- Better than 0.000,000,000,1 Seconds
		time-000-000-000-000-05 (37), -- Better than 0.000,000,000,05 Seconds
		time-000-000-000-000-02 (38), -- Better than 0.000,000,000,02 Seconds
		time-000-000-000-000-01 (39) -- Better than 0.000,000,000,01 Seconds
	}

END

Map DEFINITIONS AUTOMATIC TAGS ::= BEGIN

-- imports and exports

EXPORTS MapData, NodeID, NodeReferenceID, MovementList, LaneID, DescriptiveName, LaneWidth, PointList, SpeedLimitList, LaneAttributes, AllowedManeuvers, ConnectsToList, MovementEx;
IMPORTS MinuteOfTheYear FROM DefTime
		MsgCount FROM MsgFrame
		Speed FROM DefMotion
		Position3D FROM DefPosition
		PositionOffsetLLV FROM DefPositionOffset
		PhaseID FROM SignalPhaseAndTiming
		Polygon FROM SensorSharing;
	
	MapData ::=	SEQUENCE {
		msgCnt MsgCount,
		timeStamp MinuteOfTheYear OPTIONAL,
		nodes NodeList,
		-- intersections or road endpoints
		...
	}
	
	NodeList ::= SEQUENCE (SIZE(1..32)) OF Node
	
	Node ::= SEQUENCE {
		-- intersection or road endpoint
		name DescriptiveName OPTIONAL,
		-- Node name
		id NodeReferenceID,
		-- A globally unique value set,
		-- consisting of a regionID and
		-- node ID assignment
		refPos Position3D, 
		-- 3D position of the center of this Node.
		-- This position is also the reference position for the elements inside
		
		-- Link list using Day I format --------------------------------------
		inLinks LinkList OPTIONAL,
		-- all the links enter this Node
		
		...,
		
		-- Day II Extension--------------------------------------
		inLinks-ex LinkExList OPTIONAL,
		-- all the links enter this Node
		prohibitedzone ProhibitedZone OPTIONAL,
		...
	}
	
	DescriptiveName ::= IA5String (SIZE(1..63))
	
	NodeReferenceID ::= SEQUENCE {
		region RoadRegulatorID OPTIONAL,
		-- a globally unique regional assignment value
		-- typical assigned to a regional DOT authority
		-- the value zero shall be used for testing needs
		id NodeID
		-- a unique mapping to the node
		-- in question within the above region of use		
		}
	
	RoadRegulatorID ::= INTEGER (0..65535)
	-- The value zero shall be used for testing only
	
	NodeID ::= INTEGER (0..65535)
	-- The values zero through 255 are allocated for testing purposes 
	-- Note that the value assigned to a node will be 
	-- unique within a given regional ID only
	
	LinkList ::= SEQUENCE (SIZE(1..32)) OF Link
	
	Link ::= SEQUENCE {
		name DescriptiveName OPTIONAL,
		-- Link name
		
		upstreamNodeId NodeReferenceID,
		-- this link is from upstreamNode to the Node it belongs to
		
		speedLimits SpeedLimitList OPTIONAL,
		-- List all the speed limits
		
		linkWidth LaneWidth,
		-- Width of this link
		
		points PointList OPTIONAL,
		-- Define road points along the center of this link
		
		movements MovementList OPTIONAL,
		-- Define movements at intersection
		
		lanes LaneList,
		-- Lanes belong to this link
		...
	}
	
	MovementList ::= SEQUENCE (SIZE(1..32)) OF Movement
	
	Movement ::= SEQUENCE {
		remoteIntersection NodeReferenceID,
		-- This entry indicates the downstream intersection of the link this lane connects to. 
		-- This provides a means to create meshes of lanes
		
		phaseId PhaseID OPTIONAL
		-- The matching signal group send by
		-- the SPAT message for this lane/maneuver.
		-- Shall be present unless the connectingLane
		-- has no signal group (is un-signalized)
	}
	
	LaneList ::= SEQUENCE (SIZE(1..32)) OF Lane
	
	Lane ::= SEQUENCE {
		laneID LaneID,
		-- The unique ID number assigned
		-- to this lane object
		laneWidth LaneWidth OPTIONAL,
		laneAttributes LaneAttributes OPTIONAL,
		-- Define basic attribute of lane
		maneuvers AllowedManeuvers OPTIONAL,
		-- the permitted maneuvers for this lane
		connectsTo ConnectsToList OPTIONAL,	
		-- connection to downsteam lanes
		speedLimits SpeedLimitList OPTIONAL,
		-- List all the speed limits
		points PointList OPTIONAL,
		-- Define road points and segments
		...
	}
	
	LaneID ::= INTEGER (0..255) 
	-- the value 0 shall be used when the lane ID is 
	-- not available or not known 
	-- the value 255 is reserved for future use
	
	LaneWidth ::= INTEGER (0..32767) 
	-- units of 1 cm
	
	ConnectsToList ::= SEQUENCE (SIZE(1..8)) OF Connection
	
	Connection::= SEQUENCE {
		remoteIntersection NodeReferenceID,
		-- This entry indicates the downstream intersection of the link this lane connects to. 
		-- This provides a means to create meshes of lanes
		connectingLane ConnectingLane OPTIONAL,
		-- The index of the connecting lane and also
		-- the maneuver from the current lane to it
		-- When we want to list the allowed lanes of the next link
		-- this lane can lead to, we use this entry
		phaseId PhaseID OPTIONAL
		-- The matching signal group send by
		-- the SPAT message for this lane/maneuver.
		-- Shall be present unless the connectingLane
		-- has no signal group (is un-signalized)
	}
	
	ConnectingLane ::= SEQUENCE {
		lane LaneID, 
		-- Index of the connecting lane
		maneuver AllowedManeuvers OPTIONAL
		-- The Maneuver between
		-- the enclosing lane and this lane
		-- at the stop line to connect them
		}
	
	AllowedManeuvers ::= BIT STRING {
		-- With bits as defined:
		-- Allowed maneuvers at path end (stop line)
		-- All maneuvers with bits not set are therefore prohibited
		-- A value of zero shall be used for unknown, indicating no Maneuver
		maneuverStraightAllowed (0),
		-- a Straight movement is allowed in this lane
		maneuverLeftAllowed (1),
		-- a Left Turn movement is allowed in this lane
		maneuverRightAllowed (2),
		-- a Right Turn movement is allowed in this lane
		maneuverUTurnAllowed (3),
		-- a U turn movement is allowed in this lane
		maneuverLeftTurnOnRedAllowed (4),
		-- a Stop, and then proceed when safe movement
		-- is allowed in this lane
		maneuverRightTurnOnRedAllowed (5),
		-- a Stop, and then proceed when safe movement
		-- is allowed in this lane
		maneuverLaneChangeAllowed (6),
		-- a movement which changes to an outer lane
		-- on the egress side is allowed in this lane
		-- (example: left into either outbound lane)
		maneuverNoStoppingAllowed (7),
		-- the vehicle should not stop at the stop line
		-- (example: a flashing green arrow)
		yieldAllwaysRequired (8),
		-- the allowed movements above are not protected
		-- (example: an permanent yellow condition)
		goWithHalt (9),
		-- after making a full stop, may proceed
		caution (10),
		-- proceed past stop line with caution
		reserved1 (11)
		-- used to align to 12 Bit Field
		} (SIZE(12))
	
	LaneAttributes ::= SEQUENCE {
		shareWith LaneSharing OPTIONAL,
		laneType LaneTypeAttributes
	}
	
	LaneSharing ::= BIT STRING {
		-- With bits as defined:
		overlappingLaneDescriptionProvided (0),
		-- Assert when another lane object is present to describe the
		-- path of the overlapping shared lane
		-- this construct is not used for lane objects which simply cross
		multipleLanesTreatedAsOneLane (1),
		-- Assert if the lane object path and width details represents
		-- multiple lanes within it that are not further described
		-- Various modes and type of traffic that may share this lane:
		otherNonMotorizedTrafficTypes (2), -- horse drawn etc.
		individualMotorizedVehicleTraffic (3),
		busVehicleTraffic (4),
		taxiVehicleTraffic (5),
		pedestriansTraffic (6),
		cyclistVehicleTraffic (7),
		trackedVehicleTraffic (8),
		pedestrianTraffic (9)
	} (SIZE (10))
		-- All zeros would indicate 'not shared' and 'not overlapping'
		
	LaneTypeAttributes ::= CHOICE {
		vehicle LaneAttributes-Vehicle, -- motor vehicle lanes
		crosswalk LaneAttributes-Crosswalk, -- pedestrian crosswalks
		bikeLane LaneAttributes-Bike, -- bike lanes
		sidewalk LaneAttributes-Sidewalk, -- pedestrian sidewalk paths
		median LaneAttributes-Barrier, -- medians & channelization
		striping LaneAttributes-Striping, -- roadway markings
		trackedVehicle LaneAttributes-TrackedVehicle, -- trains and trolleys
		parking LaneAttributes-Parking, -- parking and stopping lanes
		...
	}
		
	LaneAttributes-Vehicle ::= BIT STRING { 
		-- With bits as defined:
		isVehicleRevocableLane (0),
		-- this lane may be activated or not based
		-- on the current SPAT message contents
		-- if not asserted, the lane is ALWAYS present
		isRampLane (1),
		-- Redefined in Day II Standard
		hovLaneUseOnly (2),
		restrictedToBusUse (3),
		restrictedToTaxiUse (4),
		restrictedFromPublicUse (5),
		emergencyLane (6),
		-- Redefined in Day II Standard
		permissionOnRequest (7)
		-- e.g. to inform about a lane for e-cars
	} (SIZE (8,...))
		
	LaneAttributes-Crosswalk ::= BIT STRING { 
		-- With bits as defined: 
		-- MUTCD provides no suitable "types" to use here
		crosswalkRevocableLane (0),
		-- this lane may be activated or not based
		-- on the current SPAT message contents
		-- if not asserted, the lane is ALWAYS present
		bicyleUseAllowed (1),
		-- The path allows bicycle traffic,
		-- if not set, this mode is prohibited
		isXwalkFlyOverLane (2),
		-- path of lane is not at grade
		fixedCycleTime (3),
		-- ped walk phases use preset times
		-- i.e. there is not a 'push to cross' button
		biDirectionalCycleTimes (4),
		-- ped walk phases use different SignalGroupID
		-- for each direction. The first SignalGroupID
		-- in the first Connection represents 'inbound'
		-- flow (the direction of travel towards the first
		-- node point) while second SignalGroupID in the
		-- next Connection entry represents the 'outbound'
		-- flow. And use of RestrictionClassID entries
		-- in the Connect follow this same pattern in pairs.
		hasPushToWalkButton (5),
		-- Has a demand input
		audioSupport (6),
		-- audio crossing cues present
		rfSignalRequestPresent (7),
		-- Supports RF push to walk technologies
		unsignalizedSegmentsPresent (8)
		-- The lane path consists of one of more segments
		-- which are not part of a signal group ID
		-- Bits 9~15 reserved and set to zero
	} (SIZE (16))
	
	LaneAttributes-Bike ::= BIT STRING { 
		-- With bits as defined:
		bikeRevocableLane (0),
		-- this lane may be activated or not based
		-- on the current SPAT message contents
		-- if not asserted, the lane is ALWAYS present
		pedestrianUseAllowed (1),
		-- The path allows pedestrian traffic,
		-- if not set, this mode is prohibited
		isBikeFlyOverLane (2),
		-- path of lane is not at grade
		fixedCycleTime (3),
		-- the phases use preset times
		-- i.e. there is not a 'push to cross' button
		biDirectionalCycleTimes (4),
		-- ped walk phases use different SignalGroupID
		-- for each direction. The first SignalGroupID
		-- in the first Connection represents 'inbound'
		-- flow (the direction of travel towards the first
		-- node point) while second SignalGroupID in the
		-- next Connection entry represents the 'outbound'
		-- flow. And use of RestrictionClassID entries
		-- in the Connect follow this same pattern in pairs.
		isolatedByBarrier (5),
		unsignalizedSegmentsPresent (6)
		-- The lane path consists of one of more segments
		-- which are not part of a signal group ID
		-- Bits 7~15 reserved and set to zero
	} (SIZE (16))
		
	LaneAttributes-Sidewalk ::= BIT STRING { 
		-- With bits as defined:
		sidewalk-RevocableLane (0),
		-- this lane may be activated or not based
		-- on the current SPAT message contents
		-- if not asserted, the lane is ALWAYS present
		bicyleUseAllowed (1),
		-- The path allows bicycle traffic,
		-- if not set, this mode is prohibited
		isSidewalkFlyOverLane (2),
		-- path of lane is not at grade
		walkBikes (3)
		-- bike traffic must dismount and walk 
		-- Bits 4~15 reserved and set to zero
	} (SIZE (16))
		
	LaneAttributes-Barrier ::= BIT STRING { 
		-- With bits as defined:
		median-RevocableLane (0),
		-- this lane may be activated or not based
		-- on the current SPAT message contents
		-- if not asserted, the lane is ALWAYS present
		median (1),
		whiteLineHashing (2),
		stripedLines (3),
		doubleStripedLines (4),
		trafficCones (5),
		constructionBarrier (6),
		trafficChannels (7),
		lowCurbs (8),
		highCurbs (9) -- Bits 10~15 reserved and set to zero
	} (SIZE (16))
		
	LaneAttributes-Striping ::= BIT STRING { 
		-- With bits as defined:
		stripeToConnectingLanesRevocableLane (0),
		-- this lane may be activated or not activated based
		-- on the current SPAT message contents
		-- if not asserted, the lane is ALWAYS present
		stripeDrawOnLeft (1),
		stripeDrawOnRight (2),
		-- which side of lane to mark
		stripeToConnectingLanesLeft (3),
		stripeToConnectingLanesRight (4),
		stripeToConnectingLanesAhead (5)
		-- the stripe type should be
		-- presented to the user visually
		-- to reflect stripes in the
		-- intersection for the type of
		-- movement indicated 
		-- Bits 6~15 reserved and set to zero
	} (SIZE (16))
		
	LaneAttributes-TrackedVehicle ::= BIT STRING { 
		-- With bits as defined:
		spec-RevocableLane (0),
		-- this lane may be activated or not based
		-- on the current SPAT message contents
		-- if not asserted, the lane is ALWAYS present
		spec-commuterRailRoadTrack (1),
		spec-lightRailRoadTrack (2),
		spec-heavyRailRoadTrack (3),
		spec-otherRailType (4) -- Bits 5~15 reserved and set to zero
	} (SIZE (16))
		
	LaneAttributes-Parking ::= BIT STRING {
		-- With bits as defined:
		-- Parking use details, note that detailed restrictions such as
		-- allowed hours are sent by way of ITIS codes in the TIM message
		parkingRevocableLane (0),
		-- this lane may be activated or not based
		-- on the current SPAT message contents
		-- if not asserted, the lane is ALWAYS present
		parallelParkingInUse (1),
		headInParkingInUse (2),
		doNotParkZone (3),
		-- used to denote fire hydrants as well as
		-- short disruptions in a parking zone
		parkingForBusUse (4),
		parkingForTaxiUse (5),
		noPublicParkingUse (6)
		-- private parking, as in front of
		-- private property 
		-- Bits 7~15 reserved and set to zero
	} (SIZE (16))
	
	SpeedLimitList ::= SEQUENCE (SIZE(1..9)) OF RegulatorySpeedLimit
	
	RegulatorySpeedLimit ::= SEQUENCE {
		type SpeedLimitType,
		-- The type of regulatory speed which follows
		speed Speed
		-- The speed in units of 0.02 m/s
		-- See Section 11 for converting and translating
		-- speed expressed in mph into units of m/s
		}
	
	SpeedLimitType ::= ENUMERATED {
		unknown, -- Speed limit type not available
		maxSpeedInSchoolZone, -- Only sent when the limit is active
		maxSpeedInSchoolZoneWhenChildrenArePresent, -- Sent at any time
		maxSpeedInConstructionZone, -- Used for work zones, incident zones, etc.
		-- where a reduced speed is present
		vehicleMinSpeed,
		vehicleMaxSpeed, -- Regulatory speed limit for general traffic
		vehicleNightMaxSpeed,
		truckMinSpeed,
		truckMaxSpeed,
		truckNightMaxSpeed,
		vehiclesWithTrailersMinSpeed,
		vehiclesWithTrailersMaxSpeed,
		vehiclesWithTrailersNightMaxSpeed,
		...
	}
	
	PointList ::= SEQUENCE (SIZE(2..31)) OF RoadPoint
	-- At least 2 points of 1 lane
	-- entry line and exit line
	-- points need to be listed sequentially
	-- from upstream to downstream
	
	RoadPoint ::= SEQUENCE {
		posOffset PositionOffsetLLV,
		-- Position offset to the reference position
		...
	}
	
	-- Day II Extension--------------------------------
	LinkExList ::= SEQUENCE (SIZE(1..32)) OF LinkEx
	
	LinkEx ::= SEQUENCE {
		name DescriptiveName OPTIONAL,
		-- Link name
		
		upstreamNodeId NodeReferenceID,
		-- this link is from upstreamNode to the Node it belongs to
		
		speedLimits SpeedLimitList OPTIONAL,
		-- List all the speed limits
		
		linkWidth LaneWidth OPTIONAL,
		-- Width of this link
		
		refLine PointList OPTIONAL,
		-- Define reference line of this link
		-- Using the points list from upstream to downstream
		-- along the center of lane 0 of this link
		-- Ref. line must cover the whole link, from the link entrance to the stop line
		
		movements-ex MovementExList OPTIONAL,
		-- Define movements at intersection
		
		sections SectionList,
		-- Link sections belong to this link
		-- listed from upstream to downstream
		-- Different sections are generally seperated according to lane increase or decrease
		...
	}
	
	MovementExList ::= SEQUENCE (SIZE(1..32)) OF MovementEx
	
	MovementEx ::= SEQUENCE {
		remoteIntersection NodeReferenceID,
		-- This entry indicates the downstream intersection of the link this lane connects to. 
		-- This provides a means to create meshes of lanes
		
		phaseId PhaseID OPTIONAL,
		-- The matching signal group send by
		-- the SPAT message for this lane/maneuver.
		-- Shall be present unless the connectingLane
		-- has no signal group (is un-signalized)
		
		turn-direction Maneuver OPTIONAL,
		-- Indicating the turn direction corresponding to this movement
		
		...
	}
	
	Maneuver ::= ENUMERATED {
		maneuverStraight (0),
		maneuverLeftTurn (1),
		maneuverRightTurn (2),
		maneuverUTurn (3),
		...
	}
	
	SectionList ::= SEQUENCE (SIZE(1..16)) OF Section
	
	Section ::= SEQUENCE {
		secId SectionId,
		-- Section id is distributed from upstream to downstream
		-- with 1, 2, 3, ..., sequentially
		lanes LaneExList,
		-- Lanes belong to this link
		...
	}
	
	SectionId ::= INTEGER (1..63) 
	
	LaneExList ::= SEQUENCE (SIZE(1..32)) OF LaneEx
	
	LaneEx ::= SEQUENCE {
		laneRefID LaneRefID,
		-- Lane reference id related to reference line of this link
		-- Ref. line belongs to lane ref. id 0
		-- Lane ref. ids on the left side of ref. line should be 1, 2, 3... in sequence
		-- Ref. ids on the right side should be -1, -2, -3... in sequence
		laneWidth LaneWidth OPTIONAL,
		laneAttributes LaneAttributes OPTIONAL,
		-- Define basic attribute of lane
		maneuvers AllowedManeuvers OPTIONAL,
		-- the permitted maneuvers for this lane
		connectsTo-ex ConnectsToExList OPTIONAL,
		-- connection to downsteam lanes
		speedLimits SpeedLimitList OPTIONAL,
		-- List all the speed limits
		st-points STPointList OPTIONAL,
		-- Points list of the center of this lane
		-- using ST coordinates
		laneLineType LaneLineType OPTIONAL,
		...
	}
	
	LaneLineType ::= SEQUENCE{
		leftLaneLine Dotted-SolidMarkingLineType,
		rightLaneLine Dotted-SolidMarkingLineType
	}
	
	Dotted-SolidMarkingLineType::= ENUMERATED {
		whiteDottedLine(0),
		whiteSolidLine(1),
		yellowDottedLine(2),
		yellowSolidLine(3),
		whiteDotted-solidLine(4),
		-- 白色虚实线（内侧为虚线） ，可临时跨越同向车道
		whiteSotted-dottedLine(5),
		-- 白色实虚线 （内侧为实线），同向车道可临时跨越至本车道，本车道禁止跨越到同向车道
		yellowDotted-solidLine(6),
		--黄色虚实线（内侧为虚线），可临时跨越对向车道
		yellowSotted-dottedLine(7),
		--黄色虚实线（内侧为实线），对向车道可临时跨越至本车道，本车道禁止跨越到对向车道
		...
	}
	
	LaneRefID ::= INTEGER (-31..31) 
	
	ConnectsToExList ::= SEQUENCE (SIZE(1..32)) OF ConnectionEx
	
	ConnectionEx::= SEQUENCE {
		remoteIntersection NodeReferenceID,
		-- This entry indicates the downstream intersection of the link this lane connects to. 
		-- This provides a means to create meshes of lanes
		
		swl SignalWaitingLane OPTIONAL,
		-- waiting area for certain signal phase
		-- usually set for left turn
		
		connectingLane SEQUENCE (SIZE(1..16)) OF ConnectingLaneEx OPTIONAL,
		-- The index of the connecting lane and also
		-- the maneuver from the current lane to it
		-- When we want to list the allowed lanes of the next link
		-- this lane can lead to, we use this entry
		
		phaseId PhaseID OPTIONAL,
		-- The matching signal group send by
		-- the SPAT message for this lane/maneuver.
		-- Shall be present unless the connectingLane
		-- has no signal group (is un-signalized)
		
		turn-direction Maneuver OPTIONAL,
		-- Indicating the turn direction corresponding to this movement
		...
	}
	
	SignalWaitingLane ::= SEQUENCE {
		laneWidth LaneWidth,
		points PointList,
		allowedPhaseIds SEQUENCE (SIZE(1..7)) OF PhaseID OPTIONAL
		-- e.g. for a typiccal left turn waiting area, both left turn phase and go straight phase are allowed
	}
	
	ConnectingLaneEx ::= SEQUENCE {
		target-section SectionId,
		target-lane LaneRefID, 
		-- Index of the connecting lane
		
		connectingLaneWidth LaneWidth OPTIONAL,
		-- Indicating the width of the real or virtual connecting lane
		connectingLanePoints PointList OPTIONAL,
		-- Indicating the position of the real or virtual connecting lane
		isolatedConnectingLane BOOLEAN OPTIONAL
		-- A real isolated connecting lane is seperated from any other lanes
		-- Usually exists in right turning
	}
	
	STPointList ::= SEQUENCE (SIZE(2..63)) OF ST-Point
	
	ST-Point ::= SEQUENCE {
		s-axis INTEGER (-1024..65535),
		-- Unit 0.1m
		-- Longitudinal length related to the ref. line
		t-axis INTEGER (-32768..32767),
		-- Unit 0.01m
		-- Latitudinal distance in st coordinates
		-- Positive in the left of ref. line
		-- Negative in the right of ref. line
		...
	}
	
	ProhibitedZone ::= SEQUENCE {
		centralCircleProhibitedZone Polygon OPTIONAL,
		non-motorVehicleProhibitedZones SEQUENCE (SIZE(1..16)) OF Polygon OPTIONAL,
		gridLineMarkingProhibitedZones SEQUENCE (SIZE(2..16)) OF Polygon OPTIONAL,
		-- Gird line marking prohibited zones 
		-- inside the node(intersection) or at the in-links of this node
		...
	}

	
END

MsgDayII DEFINITIONS AUTOMATIC TAGS ::= BEGIN

-- imports and exports
	
EXPORTS MessageFrameExt;
IMPORTS RTCMcorrections FROM RTCM
		PAMData FROM PAM
		CLPMM FROM Platooning
		PersonalSafetyMessage FROM PSM
		RoadsideCoordination FROM RSC
		SensorSharingMsg FROM SensorSharing
		VehIntentionAndRequest FROM VIR
		VehiclePaymentMessage FROM VPM
		TestMsg FROM TestMsg;
	
	MessageFrameExt ::= SEQUENCE {
		messageId MESSAGE-ID-AND-TYPE.&id({MessageTypes}),
		value MESSAGE-ID-AND-TYPE.&Type({MessageTypes}{@.messageId}),
		...
	}
	
	-- zyy for python, fix compile error
	-- MESSAGE-ID-AND-TYPE ::= CLASS {
	-- 	&id ExtMsgID UNIQUE,
	-- 	&Type
	-- }

	-- zyy for python, fix compile error
	-- MessageTypes MESSAGE-ID-AND-TYPE ::= {
	-- 	{ &id testData, &Type TestMsg } |	
	-- 	{ &id rtcmData, &Type RTCMcorrections } |
	-- 	{ &id pamData, &Type PAMData } |
	-- 	{ &id clpmmData, &Type CLPMM } |
	-- 	{ &id psmData, &Type PersonalSafetyMessage } |
	-- 	{ &id rscData, &Type RoadsideCoordination } |
	-- 	{ &id ssmData, &Type SensorSharingMsg } |
	-- 	{ &id virData, &Type VehIntentionAndRequest } |
	-- 	{ &id vpmData, &Type VehiclePaymentMessage },
	-- 	...
	-- }

	MESSAGE-ID-AND-TYPE ::= CLASS {
		&id ExtMsgID UNIQUE,
		&Type
	} WITH SYNTAX {&Type IDENTIFIED BY &id}

	MessageTypes MESSAGE-ID-AND-TYPE ::= {
		{ TestMsg IDENTIFIED BY testData } |	
		{ RTCMcorrections IDENTIFIED BY rtcmData } |
		{ PAMData IDENTIFIED BY pamData } |
		{ CLPMM IDENTIFIED BY clpmmData } |
		{ PersonalSafetyMessage IDENTIFIED BY psmData } |
		{ RoadsideCoordination IDENTIFIED BY rscData } |
		{ SensorSharingMsg IDENTIFIED BY ssmData } |
		{ VehIntentionAndRequest IDENTIFIED BY virData } |
		{ VehiclePaymentMessage IDENTIFIED BY vpmData },
		...
	}
	
	ExtMsgID ::= INTEGER (0..32767) 
	
	-- Test Message
	testData ExtMsgID ::= 0
	
	-- DAY II Messages *********************
	rtcmData ExtMsgID ::= 10
	rscData ExtMsgID ::= 11
	ssmData ExtMsgID ::= 12
	virData ExtMsgID ::= 13
	pamData ExtMsgID ::= 14
	psmData ExtMsgID ::= 15
	clpmmData ExtMsgID ::= 16
	vpmData ExtMsgID ::= 17
	
END

MsgFrame DEFINITIONS AUTOMATIC TAGS ::= BEGIN

-- imports and exports

EXPORTS MsgCount;
IMPORTS BasicSafetyMessage FROM BSM 
		MapData FROM Map
		RoadsideSafetyMessage FROM RSM
		SPAT FROM SignalPhaseAndTiming
		RTCMcorrections FROM RTCM
		RoadSideInformation FROM RSI
		MessageFrameExt FROM MsgDayII;

	-- Main message frame
	MessageFrame ::= CHOICE {
		-- Day 1 message frames ------------------
		bsmFrame BasicSafetyMessage,
		mapFrame MapData,
		rsmFrame RoadsideSafetyMessage,
		spatFrame SPAT,
		rsiFrame RoadSideInformation,
		
		...,
		
		-- Day 2 message frames ------------------
		msgFrameExt MessageFrameExt,
		
		...
	}
	
	MsgCount ::= INTEGER (0..127)
	
END

PAM DEFINITIONS AUTOMATIC TAGS ::= BEGIN

-- imports and exports

EXPORTS PAMData, ParkingType;
IMPORTS MinuteOfTheYear FROM DefTime
		MsgCount FROM MsgFrame
		Position3D FROM DefPosition
		DescriptiveName, LaneWidth, PointList FROM Map
		Speed FROM DefMotion
		PositionOffsetLLV FROM DefPositionOffset;
	
	PAMData ::=	SEQUENCE {
		msgCnt MsgCount,
		timeStamp MinuteOfTheYear OPTIONAL,
		parkingLotInfo ParkingLotInfo,
		-- Basic info of this parking area
		pamNodes PAMNodeList,
		-- intersections or road endpoints in parking area
		
		parkingAreaGuidance SEQUENCE (SIZE(1..16)) OF ParkingGuide OPTIONAL,
		-- parking area path guidance for individual vehicles
		-- are list here.
		
		...
	}
	
	ParkingLotInfo ::= SEQUENCE {
		id INTEGER (0..65535) OPTIONAL,
		-- Unique id of this parking lot
		-- if exists
		name DescriptiveName OPTIONAL,
		-- Name of this parking lot
		number INTEGER (0..65535) OPTIONAL,
		-- Total number of parking slots
		buildingLayerNum INTEGER (0..256) OPTIONAL,
		-- Layer number of this parking lot
		avpType AVPType OPTIONAL,
		-- AVP type
		...
	}
	
	AVPType ::=  ENUMERATED {
		p0(0),
		-- Original parking lot
		p1(1),
		-- Standard parking lot
		p2(2),
		-- Parking lot with special identification
		p3(3),
		-- Parking lot with roadside infrastructure
		p4(4),
		-- Parking lot with roadside infrastructure and V2X
		p5(5),
		-- AVP dedicated parking lot
		...
	}
	
	PAMNodeList ::= SEQUENCE (SIZE(1..63)) OF PAMNode
	
	PAMNode ::= SEQUENCE {
		-- intersection or road endpoint in parking area
		id PAMNodeID,
		-- A local unique value set
		refPos Position3D, 
		-- 3D position of the center of this Node.
		-- This position is also the reference position for the elements inside
		floor INTEGER (-128..128) OPTIONAL,
		attributes PAMNodeAttributes OPTIONAL,
		inDrives PAMDriveList OPTIONAL,
		-- all the links enter this Node
		...
	}
	
	PAMNodeID ::= INTEGER (0..65535)
	-- The values zero through 255 are allocated for testing purposes 
	-- Note that the value assigned to a node will be 
	-- unique within a parking area
	
	PAMNodeAttributes ::= BIT STRING {
		entrance(0),
		exit(1),
		toUpstair(2),
		toDownstair(3),
		etc(4),
		mtc(5),
		passAfterPayment(6),
		blocked(7)
	} (SIZE(8,...))
	
	PAMDriveList  ::= SEQUENCE (SIZE(1..63)) OF PAMDrive
	
	PAMDrive ::= SEQUENCE {
		upstreamPAMNodeId PAMNodeID,
		-- this drive is from upstreamPAMNode to the PAMNode it belongs to
		driveID INTEGER (0..255) OPTIONAL,
		-- local id of this drive with same upsttramPAMNode and PAMNode 
		twowaySepration BOOLEAN OPTIONAL,
		-- whether is this drive separated with the opposite direction.
		-- if not, then the parking slots of the opposite drive
		-- is also available for vehicles in this drive direction
		speedLimit Speed OPTIONAL,
		-- Speed limit
		heightRestriction INTEGER (0..100) OPTIONAL,
		-- Height restriction, Unit = 0.1m
		driveWidth LaneWidth OPTIONAL,
		-- Width of this drive
		laneNum INTEGER (0..100) OPTIONAL,
		-- Number of lanes
		points PointList OPTIONAL,
		-- Define road points along the center of this link
		movements PAMMovementList OPTIONAL,
		-- Define movements at intersection
		parkingSlots ParkingSlots OPTIONAL,
		-- Information of parking places of this drive
		...
	}
	
	PAMMovementList ::= SEQUENCE (SIZE(1..32)) OF PAMNodeID
	
	ParkingSlots ::= SEQUENCE (SIZE(1..256)) OF ParkingSlot
	
	ParkingSlot ::= SEQUENCE {
		slotID INTEGER (0..65535),
		position ParkingSlotPosition OPTIONAL,
		sign DescriptiveName OPTIONAL,
		-- Parking slot sign like "B101"
		parkingType ParkingType,
		status SlotStatus,
		parkingSpaceTheta ParkingSpaceTheta,
		parkingLock ParkingLock,
		...
	}
	
	ParkingSlotPosition ::= SEQUENCE {
		topLeft PositionOffsetLLV,
		topRight PositionOffsetLLV,
		bottomLeft PositionOffsetLLV
		
		-- A typical parking slot is a rectangle
		-- with four corners and four edges.
		-- The top edge is defined as the edge where a parking vehicle enters
	}
	
	ParkingLock ::= ENUMERATED {
		unknown(0),
		nolock(1),
		locked(2),
		unlocked(3),
		...
	}
	
	ParkingSpaceTheta ::= ENUMERATED {
		unknown(0),
		vertical(1),
		side(2),
		oblique(3),
		...
	}
	
	SlotStatus ::= ENUMERATED {
		unknown(0),
		available(1),
		occupied(2),
		reserved(3),
		...
	}
	
	ParkingType ::=  BIT STRING {
		unknown(0),
		ordinary(1),
		disabled(2),
		mini(3),
		attached(4),
		charging(5),
		stereo(6),
		lady(7),
		extended(8),
		private(9)
	}(SIZE(10,...))
	
	ParkingGuide ::= SEQUENCE {
		vehId OCTET STRING (SIZE(8)),
		-- temperary vehicle ID
		
		drivePath SEQUENCE (SIZE(1..32)) OF PAMNodeID,
		-- the planned path for this vehicle
		-- represented by a series of PAMNode id
		-- in order from origin to destination
		
		targetParkingSlot INTEGER (0..65535) OPTIONAL,
		-- if the vehicle is looking for a parking slot,
		-- then here is the recommended parking slot id,
		-- which should be by the last drive road in above drivePath.
		-- if a targetParkingSlot is not included in a ParkingGuide,
		-- then probably the vehicle is going to the last PAMNode
		-- whatever type the PAMNode is.
		
		...
	}
	
END

Platooning DEFINITIONS AUTOMATIC TAGS ::= BEGIN

-- imports and exports

EXPORTS CLPMM;
IMPORTS DSecond, TimeConfidence FROM DefTime
		MsgCount FROM MsgFrame;
	
	CLPMM ::= SEQUENCE {
		msgCnt MsgCount,
		id OCTET STRING (SIZE(8)),
		-- temperary vehicle ID
		secMark DSecond,
		pid OCTET STRING (SIZE(17)),
		-- Platooning ID
		role RoleInPlatooning,
		-- vehicle role
		status StatusInPlatooning,
		-- vehicle status
		leadingExt MemberManagement OPTIONAL,
		-- Platooning management information
		-- sent by the leading vehicle
		...
	}
	
	MemberManagement ::= SEQUENCE {
		memberList MemberList,
		-- member list of platooning
		joiningList MemberList OPTIONAL,
		-- list of vehicle that is allowed to join the platoon
		-- and is operating the joining procedure
		leavingList MemberList OPTIONAL,
		-- list of vehicle that is allowed to leaving the platoon
		-- and is operating the leaving procedure
		capacity INTEGER (1..32),
		-- the capacity of platooning
		openToJoin BOOLEAN,
		...
	}
	
	RoleInPlatooning ::= ENUMERATED {
		leader (0),
		follower (1),
		tail(2),
		free-vehicle(3),
		...
	}
	
	StatusInPlatooning ::= ENUMERATED {
		-- possible states of platooning members
		-- a complete platooning process can include all or part of them
		navigating (0),
		beginToDissmiss (1),
		askForJoining (2),
		joining (3),
		following (4),
		askForLeaving (5),
		leaving (6),
		...
	}
	
	MemberList ::= SEQUENCE (SIZE(1..32)) OF MemberNode
	
	MemberNode ::= SEQUENCE {	
			vid OCTET STRING (SIZE(8)),
			-- vehicle ID
			...
	}
	
END

PSM DEFINITIONS AUTOMATIC TAGS ::= BEGIN

-- imports and exports

EXPORTS PersonalSafetyMessage, Non-motorData;
IMPORTS DSecond, TimeConfidence FROM DefTime
		Speed, Heading FROM DefMotion
		Position3D, PositionConfidenceSet, PositionalAccuracy FROM DefPosition
		MsgCount FROM MsgFrame
		AccelerationSet4Way FROM DefAcceleration
		PathHistory, PathPrediction FROM VehSafetyExt
		PathPlanning FROM VIR;
	
	PersonalSafetyMessage ::= SEQUENCE {
		-- Basic Info --
		msgCnt MsgCount,
		id OCTET STRING (SIZE(8)),
		-- temperary ID
		secMark DSecond,
		timeConfidence TimeConfidence OPTIONAL,
		pos Position3D,
		posAccuracy PositionalAccuracy,
		-- Accuracy for GNSS system
		speed Speed,
		heading Heading,
		accelSet AccelerationSet4Way OPTIONAL,
		pathHistory PathHistory OPTIONAL,
		path-Planning PathPlanning OPTIONAL,
		overallRadius INTEGER (0..200),
		-- In units of one decimeter
		-- Radius considering cluster or attachment
		
		-- Type-related Data --
		non-motorData Non-motorData,
		...
	}
	
	Non-motorData ::= SEQUENCE {		
		-- Type-related Data --
		basicType PersonalDeviceUserType,
		propulsion PropelledInformation OPTIONAL,
		clusterSize NumberOfParticipantsInCluster OPTIONAL,
		attachment Attachment OPTIONAL,
		
		personalExt PersonalExtensions OPTIONAL,
		roadWorkerExt RoadWorkerExtensions OPTIONAL,
		personalReq PersonalRequest OPTIONAL,
		...
	}
	
	PersonalDeviceUserType ::= ENUMERATED {
		unavailable (0),
		aPEDESTRIAN (1),
		aPEDALCYCLIST (2),
		aROADWORKER (3),
		anANIMAL (4),
		...
	}
	
	PropelledInformation ::= CHOICE {
		human HumanPropelledType, -- PersonalDeviceUserType would be a aPEDESTRIAN
		animal AnimalPropelledType,
		motor MotorizedPropelledType,
		...
	}
	
	HumanPropelledType ::= ENUMERATED {
		unavailable (0),
		otherTypes (1),
		onFoot (2),
		skateboard (3),
		pushOrKickScooter (4),
		wheelchair (5),
		...
	}
	
	AnimalPropelledType ::= ENUMERATED {
		unavailable (0),
		otherTypes (1),
		animalMounted (2),
		animalDrawnCarriage (3),
		...
	}
	
	MotorizedPropelledType ::= ENUMERATED {
		unavailable (0),
		otherTypes (1),
		wheelChair (2),
		bicycle (3),
		scooter (4),
		selfBalancingDevice (5),
		...
	}
	
	NumberOfParticipantsInCluster ::= ENUMERATED {
		unavailable (0),
		small (1), 
		-- 2-5
		medium (2), 
		-- 6-10
		large (3), 
		-- >10
		...
	}
	
	Attachment ::= ENUMERATED {
		unavailable (0),
		stroller (1),
		bicycleTrailer (2),
		cart (3),
		wheelchair (4),
		otherWalkAssistAttachments (5),
		pet (6),
		...
	}
	
	PersonalExtensions ::= SEQUENCE {
		useState PersonalDeviceUsageState OPTIONAL,
		assistType PersonalAssistive OPTIONAL,
		...
	}
	
	PersonalDeviceUsageState ::= BIT STRING {
		unavailable (0), -- Not specified
		other (1), -- Used for states not defined below
		idle (2), -- Human is not interacting with device
		listeningToAudio (3), -- Any audio source other then calling
		typing (4), -- Including texting, entering addresses
		-- and other manual input activity
		calling (5),
		playingGames (6),
		reading (7),
		viewing (8) -- Watching dynamic content, including following
		-- navigation prompts, viewing videos or other
		-- visual contents that are not static
	} (SIZE (9, ...)) -- All bits shall be set to zero when unknown state
	
	PersonalAssistive::= BIT STRING {
		unavailable (0),
		otherType (1),
		vision (2),
		hearing (3),
		movement (4),
		cognition (5)
	} (SIZE (6, ...))
	
	RoadWorkerExtensions ::= SEQUENCE {
		workerType RoadWorkerType OPTIONAL,
		activityType RoadWorkerActivityType OPTIONAL,
		...
	}
	
	RoadWorkerType ::= ENUMERATED {
		unavailable (0),
		trafficPolice (1),
		constructionPersonnel (2),
		policeOfficers (3),
		trafficControlPersons (4),
		-- Road workers with special equipment for directing traffic.
		railroadCrossingGuards (5),
		-- Railroad crossing guards who notify motorists of approaching trains
		-- at locations like private roads or driveways crossing train tracks
		-- and where automated equipment is disabled or not present.
		emergencyOrganizationPersonnel (6),
		-- Personnel belonging to emergency response organizations such as
		-- fire departments, hospitals, river rescue, or associated with
		-- emergency vehicles including ambulances as designated by the
		-- regional authority (relating to designation of emergency vehicles)
		-- while performing their duties.
		...
	}
	
	RoadWorkerActivityType ::= BIT STRING {
		unavailable (0), -- Not specified
		workingOnRoad (1), -- Road workers on foot, in or out of
		-- a closure, performing activities like:
		-- construction, land surveying,
		-- trash removal, or site inspection.
		settingUpClosures (2), -- Road workers on foot performing
		-- activities like: setting up signs,
		-- placing cones/barrels/pylons, or placing
		-- flares. Note: People are in the road
		-- redirecting traffic, but the closure is
		-- not complete, so utmost care is required
		-- to determine the allowed path to take to
		-- avoid entering the work zone and/or
		-- harming the workers.
		respondingToEvents (3), -- Public safety or other road workers on
		-- foot performing activities like: treating
		-- injured people, putting out fires,
		-- cleaning chemical spills, aiding disabled
		-- vehicles, criminal investigations,
		-- or animal control. Note: These events tend
		-- to be more dynamic than workingOnRoad
		directingTraffic (4), -- Public safety or other road workers on
		-- foot directing traffic in situations like:
		-- a traffic signal out of operation,
		-- a construction or crash site with a short
		-- term lane closure, a single lane flagging
		-- operation, or ingress/egress to a special event.
		otherActivities (5) -- Designated by regional authorities
	} (SIZE (6, ...))
	
	PersonalRequest ::= SEQUENCE {
		crossing PersonalCrossing OPTIONAL,
		...
	}
	
	PersonalCrossing ::= ENUMERATED {
		unavailable (0),
		request (1),
		crossing (2),
		finish (3),
		...
	}
	
END

RSC DEFINITIONS AUTOMATIC TAGS ::= BEGIN

-- imports and exports

EXPORTS RoadsideCoordination;
IMPORTS MsgCount FROM MsgFrame
		DSecond, MinuteOfTheYear, TimeOffset, DDateTime FROM DefTime
		Position3D FROM DefPosition
		DriveBehavior, PathPlanning FROM VIR
		PointList FROM Map
		ReferenceLink, ReferencePath, Description FROM RSI
		Speed FROM DefMotion;
	
	RoadsideCoordination ::= SEQUENCE {
		msgCnt MsgCount,
		id OCTET STRING (SIZE(8)),
		-- temperary RSU ID
		secMark DSecond,
		refPos Position3D,
		-- Reference position of this RSC message
		coordinates SEQUENCE (SIZE(1..16)) OF VehicleCoordination OPTIONAL,
		-- Coordination with single vehicle
		laneCoordinates SEQUENCE (SIZE(1..8)) OF LaneCoordination OPTIONAL,
		-- Lane or link level coordination
		...
	}

	LaneCoordination ::= SEQUENCE {
		targetLane ReferenceLink,
		-- The target link or lane that RSU tries to control
		relatedPath ReferencePath OPTIONAL,
		-- reference path if existed to help vehicles to determine
		-- whether they should follow the coordination or not
		tBegin DDateTime OPTIONAL,
		tEnd DDateTime OPTIONAL,
		recommendedSpeed Speed OPTIONAL,
		recommendedBehavior DriveBehavior OPTIONAL,
		info CoordinationInfo OPTIONAL,
		-- Detailed use cases related to current coordination
		description Description OPTIONAL,
		-- Additional description information
		...
	}
	
	VehicleCoordination ::= SEQUENCE {
		vehId OCTET STRING (SIZE(8)),
		-- Temp ID of the target vehicle
		driveSuggestion DriveSuggestion OPTIONAL,
		pathGuidance PathPlanning OPTIONAL,
		-- Coordination using path guidance
		info CoordinationInfo OPTIONAL,
		-- Detailed use cases related to current coordination
		...
	}
	
	CoordinationInfo ::= BIT STRING {
		cooperativeLaneChanging(0),
		cooperativeVehMerging(1),
		laneChangingAtIntersection(2),
		no-signalIntersectionPassing(3),
		dynamicLaneManagement(4),
		laneReservation(5),
		laneRestriction(6),
		signalPriority(7)
	} (SIZE(8,...))
	
	DriveSuggestion ::= SEQUENCE {
		suggestion DriveBehavior,
		-- Drive behavior allowed or recommended
		-- within the time range below
		-- if matches the related link or path
		lifeTime TimeOffset OPTIONAL,
		-- Lifetime of this suggestion
		-- Time offset is calculated from secMark of this message
		relatedLink ReferenceLink OPTIONAL,
		-- Extra judgement condition for vehicle to decide whether to follow the suggestion or not
		relatedPath ReferencePath OPTIONAL,
		-- Extra judgement condition for vehicle to decide whether to follow the suggestion or not
		...
	}
	
END

RSI DEFINITIONS AUTOMATIC TAGS ::= BEGIN

-- imports and exports

EXPORTS RoadSideInformation, RTEList, ReferencePathList, ReferenceLink, Description, ReferencePath, RSITimeDetails;
IMPORTS Position3D FROM DefPosition
		MsgCount FROM MsgFrame
		MinuteOfTheYear, DSecond, TimeConfidence FROM DefTime
		PositionOffsetLLV FROM DefPositionOffset
		NodeReferenceID FROM Map
		Confidence FROM VehSafetyExt;
	
	RoadSideInformation ::= SEQUENCE {
		msgCnt MsgCount,
		moy MinuteOfTheYear OPTIONAL,
		id OCTET STRING (SIZE(8)),
		-- RSU ID
		refPos Position3D,
		-- Reference position of this RSI message
		rtes RTEList OPTIONAL,
		-- All the rte data packed in this message
		rtss RTSList OPTIONAL,
		-- All the rts data packed in this message
		...
	}
	
	-- Define Road Traffic Event ----------------------------------
	
	RTEList ::= SEQUENCE (SIZE(1..8)) OF RTEData
	-- Road Traffic Event List
	
	RTEData ::= SEQUENCE {
		rteId INTEGER (0..255),
		-- local ID of this rte information set by RSU
		eventType EventType,
		-- Type of event, according to China GB/T 29100-2012
		eventSource EventSource,
		eventPos PositionOffsetLLV OPTIONAL,
		-- Position of this event, if exists
		eventRadius Radius OPTIONAL,
		-- Radius of this event, if exists
		description Description OPTIONAL,
		-- Additional description to this event
		timeDetails RSITimeDetails OPTIONAL,
		-- Start time or end time when this event is active
		priority RSIPriority OPTIONAL,
		-- the urgency of this RSI data, a relative
		-- degree of merit compared with other RSI data
		referencePaths ReferencePathList OPTIONAL,
		-- Related paths of this traffic event
		referenceLinks ReferenceLinkList OPTIONAL,
		-- Related links of this traffic event
		eventConfidence Confidence OPTIONAL,
		-- indicate the event confidence set by event source
		-- the probability/confidence of the detected event
		-- being truly extent at a certain place, 
		-- to help vehicle determine whether to trust the received information.
		...
	}
	
	EventSource ::= ENUMERATED {
		unknown(0),	-- 0 Unknown
		police(1),	-- 1 traffic police
		government(2),	-- 2 govenment
		meteorological(3), -- 3 meteorological department
		internet(4),	-- 4 internet services
		detection(5),	-- 5 local detection
		...
	}
	
	EventType ::= INTEGER (0..65535)
	-- Traffic event type according to China GB/T 29100-2012
	
	RSITimeDetails ::= SEQUENCE {
		startTime MinuteOfTheYear OPTIONAL,
		endTime MinuteOfTheYear OPTIONAL,
		-- Exact or estimated end time
		endTimeConfidence TimeConfidence OPTIONAL
	}
	
	ReferencePathList ::= SEQUENCE (SIZE(1..8)) OF ReferencePath
	
	ReferencePath ::= SEQUENCE {
		activePath PathPointList,
		-- RSI is active for vehicles within this path
		-- Points are listed from upstream to downstream
		-- along the vehicle drive direction.
		-- One path includes at least 1 points.
		-- A path with only 1 point means a round alert area
		pathRadius Radius
		-- The biggest distance away from the alert path
		-- within which the warning is active.
	}
	
	-- Define Road Traffic Sign ----------------------------------
	
	RTSList ::= SEQUENCE (SIZE(1..16)) OF RTSData
	
	RTSData ::= SEQUENCE {
		rtsId INTEGER (0..255),
		-- local ID of this rts information set by RSU
		signType SignType,
		-- Type of sign, according to China GB 5768.2
		signPos PositionOffsetLLV OPTIONAL,
		-- Position of the traffic sign, if exists
		description Description OPTIONAL,
		-- Additional description to the sign
		timeDetails RSITimeDetails OPTIONAL,
		-- start time or end time when this sign is active, if existed
		priority RSIPriority OPTIONAL,
		-- the urgency of this RSI data, a relative
		-- degree of merit compared with other RSI data
		referencePaths ReferencePathList OPTIONAL,
		-- Related paths of this traffic sign
		referenceLinks ReferenceLinkList OPTIONAL,
		-- Related links of this traffic sign
		...,

		-- DAY II Extension 
		auxiliarySign AuxiliarySign OPTIONAL,
		-- Refer to GB5768.2-2009 Chpt.9.2
		-- Auxiliary sign
		...
	}
	
	AuxiliarySign::= SEQUENCE{
		signWithVehicleType  AuxiliarySignVehicleType OPTIONAL,
		-- 补充说明某些标志规定车辆的种类、属性，可用于表示一种或两种车辆禁止向某方向行驶的场景中
		signDirection  AuxiliarySignDirection OPTIONAL,
		-- 补充说明禁令或标志规定的方向
		...
	}
	
	AuxiliarySignVehicleType ::= BIT STRING {
		restrictedFromBus(0),
		-- 除公共汽车以外
		vehicle(1),
		-- 机动车
		truck(2),
		-- 货车
		tractor(3),
		-- 拖拉机
		private(4)
		-- 私人专属
	}(SIZE(5, ...))

	AuxiliarySignDirection::= ENUMERATED{
		straight(0),
		leftAndRight(1),
		right(2),
		left(3),
		leftFrontTurn(4),
		rightFronTurn(5),
		rightRearTurn(6),
		leftRearTurn(7),
		...
	}
	
	Description ::= CHOICE{
		textString IA5String (SIZE(1..512)),
		-- ASCII text
		textGB2312 OCTET STRING (SIZE(2..512))
		-- text using Chinese-character encoding GB2312-80
	}
	
	ReferenceLinkList ::= SEQUENCE (SIZE(1..16)) OF ReferenceLink
	
	ReferenceLink ::= SEQUENCE {
		-- this Link is from Node of upstreamNodeId to Node of downstreamNodeId
		upstreamNodeId NodeReferenceID,
		downstreamNodeId NodeReferenceID,
		referenceLanes ReferenceLanes OPTIONAL
		-- Provide reference lanes if is necessary
		-- Refer to all lanes if this data is not given
	}
	
	ReferenceLanes ::= BIT STRING {
		-- With bits as defined:
		reserved(0),
		lane1(1),
		lane2(2),
		lane3(3),
		lane4(4),
		lane5(5),
		lane6(6),
		lane7(7),
		lane8(8),
		lane9(9),
		lane10(10),
		lane11(11),
		lane12(12),
		lane13(13),
		lane14(14),
		lane15(15)
	} (SIZE (16))
	-- Set bit to 1 if the related lane is effective
	-- Support maximum 15 lanes
	
	SignType ::= INTEGER (0..65535)
	-- Traffic sign type according to China GB 5768.2
	-- Text message warning = 0
	-- Danger = 37
	-- Rockfall = 15
	-- SharpTurn = 2
	-- UnderConstruction = 38
	-- Slippy = 17
	-- Tunnel = 21
	
	PathPointList ::= SEQUENCE (SIZE(2..32)) OF PositionOffsetLLV
	-- Path point list for RTS message
	
	Radius ::= INTEGER (0..65535)
	-- Define radius
	-- Unit is 0.1m
	
	RSIPriority ::= OCTET STRING (SIZE(1))
	-- The lower five bits are reserved and shall be set to zero
	-- Value from B00000000 to B11100000 represents the lowest to the highest level
	
	-- value assignments
	
END

RSM DEFINITIONS AUTOMATIC TAGS ::= BEGIN

-- imports and exports

EXPORTS RoadsideSafetyMessage, ParticipantData, SourceType;
IMPORTS AccelerationSet4Way FROM DefAcceleration
		VehicleSize FROM VehSize
		Position3D, PositionConfidenceSet FROM DefPosition
		DSecond FROM DefTime
		Speed, Heading, SteeringWheelAngle, MotionConfidenceSet FROM DefMotion
		TransmissionState FROM VehStatus
		MsgCount FROM MsgFrame
		VehicleClassification FROM VehClass
		PositionOffsetLLV FROM DefPositionOffset;
	
	RoadsideSafetyMessage ::= SEQUENCE {
		msgCnt MsgCount,
		id OCTET STRING (SIZE(8)),
		-- RSU ID
		refPos Position3D,
		-- Reference position of this RSM message
		participants ParticipantList,
		-- All or part of the participants 
		-- detected by RSU
		...
	}
	
	ParticipantList ::= SEQUENCE (SIZE(1..16)) OF ParticipantData
	
	ParticipantData ::= SEQUENCE {
		ptcType ParticipantType,
		ptcId INTEGER (0..65535),
		-- temporary ID set by RSU
		-- 0 is RSU itself
		-- 1..255 represent participants detected by RSU
		-- ptcId of different participant needs to be unique in RSU
		source SourceType,
		id OCTET STRING (SIZE(8)) OPTIONAL,
		-- temperary vehicle ID from BSM
		secMark DSecond,
		pos PositionOffsetLLV,
		posConfidence PositionConfidenceSet,
		transmission TransmissionState OPTIONAL,
		speed Speed,
		heading Heading,
		angle SteeringWheelAngle OPTIONAL,
		motionCfd MotionConfidenceSet OPTIONAL,
		accelSet AccelerationSet4Way OPTIONAL,
		size VehicleSize,
		-- Size of participant including motor/non-motor/pedestrian/rsu
		-- is represented by DE_VehilceSize
		vehicleClass VehicleClassification OPTIONAL,
		...
	}
	
	ParticipantType ::= ENUMERATED {
		unknown (0), -- Unknown
		motor (1), -- motor
		non-motor (2), -- non-motor
		pedestrian (3), -- pedestrian
		rsu (4), -- rsu
		...
		}
	
	SourceType ::= ENUMERATED {
		unknown(0),
		selfinfo(1),
		v2x(2),
		video(3),
		microwaveRadar(4),
		loop(5),
		lidar(6),
		integrated(7),
		...
		}
	
END

RTCM DEFINITIONS AUTOMATIC TAGS ::= BEGIN

-- imports and exports

EXPORTS RTCMcorrections;
IMPORTS MsgCount FROM MsgFrame
		MinuteOfTheYear FROM DefTime
		FullPositionVector FROM VehSafetyExt;
	
	RTCMcorrections ::= SEQUENCE {
		msgCnt MsgCount,
		corrections SEQUENCE (SIZE(1..5)) OF RTCMmsg,
		...
	}	
	
	RTCMmsg ::= SEQUENCE {
		rev RTCM-Revision OPTIONAL,
		-- the message and sub-message type, as
		-- defined in the RTCM revision being used
		rtcmID RTCM-ID OPTIONAL,    
		--RTCM version number
		payload RTCM-Payload,
		-- the payload bytes
		...
	}
		 
	RTCM-ID ::= INTEGER (0..32767)
	RTCM-Payload::= OCTET STRING (SIZE(1..2047))
		
	RTCM-Revision ::= ENUMERATED {
		unknown (0),
		reserved (1),
		rtcmCMR (2),
		rtcmCMR-Plus (3),
		rtcmSAPOS (4),
		rtcmSAPOS-Adv (5),
		rtcmRTCA (6),
		rtcmRAW (7),
		rtcmRINEX (8),
		rtcmSP3 (9),
		rtcmBINEX (10),
		rtcmRev2-x (19), -- Used when specific rev is not known
		rtcmRev2-0 (20),
		rtcmRev2-1 (21),
		rtcmRev2-3 (23), -- Std 10402.3
		rtcmRev3-0 (30),
		rtcmRev3-1 (31), -- Std 10403.1
		rtcmRev3-2 (32),
		...
	}
	
END

SensorSharing DEFINITIONS AUTOMATIC TAGS ::= BEGIN

-- imports and exports

EXPORTS SensorSharingMsg, AccSet4WayConfidence, Polygon;
IMPORTS MsgCount FROM MsgFrame
		Position3D, PositionConfidenceSet FROM DefPosition
		ParticipantData, SourceType FROM RSM
		RTEList FROM RSI
		DSecond, TimeOffset FROM DefTime
		PathHistory, Confidence FROM VehSafetyExt
		ExteriorLights FROM VehStatus
		HeadingConfidence, Speed, Heading, SpeedConfidence FROM DefMotion
		YawRate, AccelerationSet4Way FROM DefAcceleration
		PositionOffsetLLV FROM DefPositionOffset
		Non-motorData FROM PSM
		DriveBehavior, PathPlanning FROM VIR;
	
	SensorSharingMsg ::= SEQUENCE {
		msgCnt MsgCount,
		id OCTET STRING (SIZE(8)),
		-- temperary vehicle ID / RSU ID
		-- who provides the sensor sharing info.
		equipmentType EquipmentType,
		-- Type of the sender
		secMark DSecond,
		sensorPos Position3D,
		-- Position of the RSU or OBU that sends this message
		-- Used as the reference position within this VSS message
		detectedRegion DetectedRegion OPTIONAL,
		-- detection area description
		--自动驾驶车辆结合目标物的输出做不同的安全策略
		participants DetectedPTCList OPTIONAL,
		-- All or part of the traffic participants 
		obstacles DetectedObstacleList OPTIONAL,
		-- All or part of Obstacles
		rtes RTEList OPTIONAL,
		-- All the rte data packed in this message
		...
	}
	
	DetectedRegion ::= SEQUENCE (SIZE(1.. 8)) OF Polygon
	
	EquipmentType ::= ENUMERATED{
		unknown (0),
		rsu (1),
		obu (2),
		vru (3),
		...
	}
	
	DetectedPTCList ::= SEQUENCE (SIZE(1..512)) OF DetectedPTCData
	-- 一个大路口的目标物可以达到300到500
	-- 实际使用时，需要考虑底层空口资源能力
	
	DetectedPTCData::= SEQUENCE {
		ptc ParticipantData,
		-- Basic information of traffic participant
		objSizeConfidence ObjectSizeConfidence OPTIONAL,
		--大小置信度
		detectedPTCType DetectedPTCType OPTIONAL,
		-- DayI中ParticipantType类型很少，考虑是扩展原有的还是将ParticipantType作为一级分类，新增字段作为二级分类
		typeConfidence Confidence OPTIONAL,
		-- 类型置信度
		acc4WayConfidence AccSet4WayConfidence OPTIONAL,
		--四轴加速度置信度
        statusDuration TimeOffset OPTIONAL,
        -- Time length for which ptc keeps the same situation
        -- Mainly used for stationary vehicle
        pathHistory PathHistory OPTIONAL,
        planningList PlanningList OPTIONAL,
        -- 路侧对被感知对象的预测可以比车端做得更优，协同预测
        tracking INTEGER (1..65535) OPTIONAL,
		-- tracking time of this obstacle
		-- in seconds
        polygon Polygon OPTIONAL,
        -- 3D vertex list
        
        type-relatedExt CHOICE { 
			motorExt MotorDataExtension,
			-- Data Extension for vehicle
	        non-motorExt Non-motorDataExtension,
	        -- Data Extension for vehicle
	        ...
		} OPTIONAL,
        ...
	}
	
	PlanningList::= SEQUENCE(SIZE(1..8)) OF Planning	
	Planning::=SEQUENCE{
		duration PlanningDuration OPTIONAL,
		-- time duration for this plan
		planConfidence Confidence OPTIONAL,
		drivingBehavior DriveBehavior OPTIONAL,
		pathPlanning PathPlanning OPTIONAL,
        ...
	}

	PlanningDuration ::= INTEGER (0..600)
	-- Unit 0.1s
	
	AccSet4WayConfidence ::= SEQUENCE {
		lonAccConfidence AccConfidence,
		latAccConfidence AccConfidence,
		vertAccConfidence AccConfidence,
		yawRateCon AngularVConfidence
	}

	AccConfidence::= ENUMERATED {
		unavailable (0), -- Not Equipped or unavailable
		prec100deg (1), -- 100 m/s2
		prec10deg (2), -- 10 m/s2
		prec5deg (3), -- 5 m/s2
		prec1deg (4), -- 1 m/s2
		prec0-1deg (5), -- 0.1 m/s2
		prec0-05deg (6), -- 0.05 m/s2
		prec0-01deg (7) -- 0.01m/s2
	}-- Encoded as a 3 bit value

	DetectedPTCType::= ENUMERATED {
		unknown (0),
		-- 未知障碍物
		unknown-movable(1),
		-- 未知可移动障碍物
		unknown-unmovable(2),
		-- 未知不可移动障碍物
		car(3),
		-- 轿车
		van(4),
		--面包车
		truck(5),
		--卡车
		bus(6),
		--大巴
		cyclist(7),
		--自行车
		motorcyclist(8),
		--摩托车
		tricyclist(9),
		--三轮车
		pedestrian(10),
		--行人
		...
		--可能会再扩展
}
 
	MotorDataExtension ::= SEQUENCE {
	    lights ExteriorLights OPTIONAL,
		vehAttitude Attitude OPTIONAL,
		vehAttitudeConfidence AttitudeConfidence OPTIONAL,
		vehAngVel AngularVelocity OPTIONAL,
		vehAngVelConfidence AngularVelocityConfidence OPTIONAL,
		...
	}
	
	Polygon ::= SEQUENCE(SIZE(4..32)) OF PositionOffsetLLV
	
	Attitude ::= SEQUENCE {
		pitch Pitch,
		roll Roll,
		yaw Yaw
	}

	Pitch ::= INTEGER (-7200..7200) 
	-- LSB units of 0.0125 degrees (signed)
	-- range of -90 to 90 degrees
	Roll ::= INTEGER (-7200..7200) 
	-- LSB units of 0.0125 degrees (signed)
	-- range of -90 to 90 degrees 
    Yaw ::= INTEGER (-14400..14400)
   	-- LSB units of 0.0125 degrees (signed)
    -- range of -180 to 180 degrees

	AttitudeConfidence ::= SEQUENCE {
		pitchConfidence HeadingConfidence,
		rollRateConfidence HeadingConfidence,
		yawRate HeadingConfidence
	}
		
	AngularVelocity ::= SEQUENCE {
		pitchRate PitchRate,
		rollRate RollRate,
		yawRate YawRate
	}

	PitchRate ::= INTEGER (-32767..32767) 
	-- LSB units of 0.01 degrees per second(signed)

	RollRate ::= INTEGER (-32767..32767) 
	-- LSB units of 0.01 degrees per second(signed)

	AngularVelocityConfidence ::= SEQUENCE {
		pitchRate AngularVConfidence,
		rollRate AngularVConfidence,
		yawRate AngularVConfidence
	}

	AngularVConfidence ::= ENUMERATED {
		unavailable (0), -- Not Equipped or unavailable
		prec100deg (1), -- 100 degree / sec
		prec10deg (2), -- 10 degree / sec
		prec5deg (3), -- 5 degree / sec
		prec1deg (4), -- 1 degree / sec
		prec0-1deg (5), -- 0.1 degree / sec
		prec0-05deg (6), -- 0.05 degree / sec
		prec0-01deg (7) -- 0.01 degree / sec
		}-- Encoded as a 3 bit value

	Non-motorDataExtension ::= SEQUENCE {
		overallRadius INTEGER (0..200),
		-- In units of one decimeter
		-- Radius considering cluster or attachment
		
		-- Type-related Data --
		non-motorData Non-motorData,
		...
	}

	DetectedObstacleList ::= SEQUENCE (SIZE(1..64)) OF DetectedObstacleData
	
	DetectedObstacleData ::= SEQUENCE {
		obsType ObstacleType,
		objTypeConfidence Confidence OPTIONAL,
		obsId INTEGER (0..65535),
		-- temporary ID set by the message sender
		-- 0 is reserved
		-- 1..255 represent different detected obstacles
		-- obsId of different participant needs to be unique locally
		source SourceType,
		secMark DSecond,
		pos PositionOffsetLLV,
		posConfidence PositionConfidenceSet,
		speed Speed,
		speedCfd SpeedConfidence OPTIONAL,
		heading Heading,
		headingCfd HeadingConfidence OPTIONAL,
		verSpeed Speed OPTIONAL,
		verSpeedConfidence SpeedConfidence OPTIONAL,
		accelSet AccelerationSet4Way OPTIONAL,
		size ObjectSize,
		objSizeConfidence ObjectSizeConfidence OPTIONAL,
		tracking INTEGER (1..65535) OPTIONAL,
		-- tracking time of this obstacle
		-- in seconds
		polygon Polygon OPTIONAL,
		-- 3D vertex list
		...
	}
	
	ObstacleType ::= ENUMERATED {
		unknown (0),
		rockfall(1),
		landslide(2),
		animal-intrusion(3),
		liquid-spill(4),
		goods-scattered(5),
		trafficcone(6),
		-- 锥筒
	    safety-triangle(7),
	    -- 三角牌
	    traffic-roadblock(8),
	    inspection-shaft-without-cover(9),
		unknown-fragments(10),
		unknown-hard-object(11),
		unknown-soft-object(12),
		...
	}
	
	ObjectSize ::= SEQUENCE {
		width SizeValue,
		length SizeValue,
		height SizeValue OPTIONAL
	}

	SizeValue ::= INTEGER (0..1023) 
	-- LSB units are 10 cm with a range of >100 meters

	ObjectSizeConfidence ::= SEQUENCE {
		widthConf SizeValueConfidence,
		lengthConf SizeValueConfidence,
		heightConf SizeValueConfidence OPTIONAL
	}
	
	SizeValueConfidence ::= ENUMERATED {
		unavailable (0),
		size-100-00 (1), -- (100 m)
		size-050-00 (2), -- (50 m)
		size-020-00 (3), -- (20 m)
		size-010-00 (4), -- (10 m)
		size-005-00 (5), -- (5 m)
		size-002-00 (6), -- (2 m)
		size-001-00 (7), -- (1 m)
		size-000-50 (8), -- (50 cm)
		size-000-20 (9), -- (20 cm)
		size-000-10 (10), -- (10 cm)
		size-000-05 (11), -- (5 cm)
		size-000-02 (12), -- (2 cm)
		size-000-01 (13) -- (1 cm)
	}

END

SignalPhaseAndTiming DEFINITIONS AUTOMATIC TAGS ::= BEGIN

-- imports and exports

EXPORTS SPAT, PhaseID, IntersectionStateList;
IMPORTS MinuteOfTheYear FROM DefTime
		DescriptiveName, NodeReferenceID FROM Map
		MsgCount FROM MsgFrame
		DSecond, TimeMark, TimeConfidence FROM DefTime
		Confidence FROM VehSafetyExt;
	
	SPAT ::= SEQUENCE {
		msgCnt MsgCount,
		moy MinuteOfTheYear OPTIONAL,
		timeStamp DSecond OPTIONAL,
		-- Time stamp when this message is formed
		name DescriptiveName OPTIONAL,
		-- human readable name for this collection
		-- to be used only in debug mode
		intersections IntersectionStateList,
		-- sets of SPAT data (one per intersection)
		...
	}
	
	IntersectionStateList ::= SEQUENCE (SIZE(1..32)) OF IntersectionState	
	
	IntersectionState ::= SEQUENCE {
		intersectionId NodeReferenceID,
		-- A globally unique value set, consisting of a
		-- regionID and intersection ID assignment
		-- provides a unique mapping to the MAP Node
		status IntersectionStatusObject,
		-- general status of the controller(s)
		moy MinuteOfTheYear OPTIONAL,
		-- Minute of current UTC year
		-- used only with messages to be archived
		timeStamp DSecond OPTIONAL,
		-- the mSec point in the current UTC minute that
		-- this message was constructed
		timeConfidence TimeConfidence OPTIONAL,
		-- indicate the time confidence of the above UTC time
		phases PhaseList,
		-- Each Movement is given in turn
		-- and contains its signal phase state,
		-- mapping to the lanes it applies to, and
		-- point in time it will end, and it
		-- may contain both active and future states
		...
	}
	
	IntersectionStatusObject ::= BIT STRING {
		manualControlIsEnabled (0),
		-- Timing reported is per programmed values, etc. but person
		-- at cabinet can manually request that certain intervals are
		-- terminated early (e.g. green).
		stopTimeIsActivated (1),
		-- And all counting/timing has stopped.
		failureFlash (2),
		-- Above to be used for any detected hardware failures,
		-- e.g. conflict monitor as well as for police flash
		preemptIsActive (3),
		signalPriorityIsActive (4),
		-- Additional states
		fixedTimeOperation (5),
		-- Schedule of signals is based on time only
		-- (i.e. the state can be calculated)
		trafficDependentOperation (6),
		-- Operation is based on different levels of traffic parameters
		-- (requests, duration of gaps or more complex parameters)
		standbyOperation (7),
		-- Controller: partially switched off or partially amber flashing
		failureMode (8),
		-- Controller has a problem or failure in operation
		off (9),
		-- Controller is switched off
		-- Related to MAP and SPAT bindings
		recentMAPmessageUpdate (10),
		-- Map revision with content changes
		recentChangeInMAPassignedLanesIDsUsed (11),
		-- Change in MAP's assigned lanes used (lane changes)
		-- Changes in the active lane list description
		noValidMAPisAvailableAtThisTime (12),
		-- MAP (and various lanes indexes) not available
		noValidSPATisAvailableAtThisTime (13)
		-- SPAT system is not working at this time
		-- Bits 14,15 reserved at this time and shall be zero
	} (SIZE(16))
		
	PhaseList ::= SEQUENCE (SIZE(1..16)) OF Phase
	-- List of phases in one traffic signal
	
	Phase ::= SEQUENCE{
		id PhaseID,
		-- the group id is used to map to lists
		-- of lanes (and their descriptions)
		-- which this MovementState data applies to
		-- see comments in the Remarks for usage details
		phaseStates PhaseStateList
		-- Consisting of sets of movement data with:
		-- a) SignalPhaseState
		-- b) TimeChangeDetails, and
		-- c) AdvisorySpeeds (optional )
		-- Note one or more of the movement events may be for
		-- a future time and that this allows conveying multiple
		-- predictive phase and movement timing for various uses
		-- for the current signal group
	}
	
	PhaseStateList ::= SEQUENCE (SIZE(1..16)) OF PhaseState
	
	PhaseState ::= SEQUENCE {
		light LightState,
		-- Consisting of:
		-- Phase state (the basic 11 states)
		-- Directional, protected, or permissive state
		timing TimeChangeDetails OPTIONAL,
		-- Timing Data in UTC time stamps for event
		-- includes start and min/max end times of phase
		-- confidence and estimated next occurrence
		...
		}
	
	LightState ::= ENUMERATED {
		unavailable (0),
		-- This state is used for unknown or error
		dark (1),
		-- The signal is dark (unlit)
		
		-- Reds
		flashing-red (2),
		-- Reserved for special scenarios
		red (3),
		-- Driver Action:
		-- Stop vehicle at stop line.
		-- Do not proceed.
		
		-- Greens
		flashing-green (4),
		-- Reserved for special scenarios		
		permissive-green (5),
		-- Driver Action:
		-- Proceed with caution,
		-- must yield to all conflicting traffic
		-- Conflicting traffic may be present
		-- in the intersection conflict area
		protected-green (6),
		-- Driver Action:
		-- Proceed, tossing caution to the wind,
		-- in indicated (allowed) direction.
		
		-- Yellows / Ambers 
		-- The vehicle is not allowed to cross the stop bar if it is possible 
		-- to stop without danger.
		yellow (7),
		-- Driver Action:
		-- Prepare to stop.
		-- Proceed if unable to stop,
		-- in indicated direction (to connected lane)
		-- Clear Intersection.
		
		flashing-yellow (8),
		-- Driver Action:
		-- Proceed with caution,
		-- Conflicting traffic may be present
		-- in the intersection conflict area
		
		...
	}
	
	TimeChangeDetails ::= CHOICE { 
		counting TimeCountingDown,
		utcTiming UTCTiming,
		...
	}
	
	UTCTiming ::= SEQUENCE {
		startUTCTime TimeMark,
		-- If already started, the value represents 
		-- the time stamp when this phase state started.
		-- If not, the value represents
		-- the time stamp when this phase state starts.
		minEndUTCTime TimeMark OPTIONAL,
		-- The time stamp when this state 1st ends in shortest time
		maxEndUTCTime TimeMark OPTIONAL,
		-- The time stamp when this state 1st ends in longest time
		likelyEndUTCTime TimeMark,
		-- The time stamp when this state 1st ends in best predicted time
		timeConfidence Confidence OPTIONAL,
		-- Confidence of likelyEndUTCTime
		nextStartUTCTime TimeMark OPTIONAL,
		-- A rough estimate of UTC time stamp when this phase state may next occur again
		-- used to support various ECO driving power management needs.
		-- If already started, this value is recommended to be delivered.
		nextEndUTCTime TimeMark OPTIONAL
		-- A rough estimate of UTC time stamp when this phase state ends again
		-- used to support various ECO driving power management needs.
		-- If already started, this value is recommended to be delivered.
	}
	
	TimeCountingDown ::= SEQUENCE {
		startTime TimeMark,
		-- When this phase state started,
		-- if already started, the value is 0
		minEndTime TimeMark OPTIONAL,
		-- Expected shortest end time
		-- the value is the min left time from now
		maxEndTime TimeMark OPTIONAL,
		-- Expected longest end time
		-- the value is the max left time from now
		likelyEndTime TimeMark,
		-- Best predicted value based on other data
		-- the value is the likely left time from now
		timeConfidence Confidence OPTIONAL,
		-- Confidence of likelyTime
		nextStartTime TimeMark OPTIONAL,
		-- A rough estimate of time from now when this phase state may next occur again
		-- used to support various ECO driving power management needs.
		-- If already started, this value is recommended to be delivered.
		nextDuration TimeMark OPTIONAL
		-- A rough estimate of the time length of this phase state
		-- when it may next occur again.
		-- used to support various ECO driving power management needs.
		-- If already started, this value is recommended to be delivered.
	}
	
	PhaseID ::= INTEGER (0..255)
	-- The value 0 shall be used when the ID is
	-- not available or not known
	-- the value 255 is reserved to indicate a
	-- permanent green movement state
	-- therefore a simple 8 phase signal controller
	-- device might use 1..9 as its groupIDs
	
END

TestMsg DEFINITIONS AUTOMATIC TAGS ::= BEGIN

-- imports and exports

EXPORTS TestMsg;
IMPORTS MsgCount FROM MsgFrame;
	
	TestMsg ::= SEQUENCE {
		msgCnt MsgCount,
		userData OCTET STRING (SIZE(1..2048))
	}
	
END

VehBrake DEFINITIONS AUTOMATIC TAGS ::= BEGIN

-- imports and exports

EXPORTS BrakeSystemStatus;
IMPORTS ;
	
	BrakeSystemStatus ::= SEQUENCE {
		brakePadel BrakePedalStatus OPTIONAL,
		wheelBrakes BrakeAppliedStatus OPTIONAL,
		traction TractionControlStatus OPTIONAL,
		abs AntiLockBrakeStatus OPTIONAL,
		scs StabilityControlStatus OPTIONAL,
		brakeBoost BrakeBoostApplied OPTIONAL,
		auxBrakes AuxiliaryBrakeStatus OPTIONAL
	}
	
	BrakePedalStatus ::= ENUMERATED {
		unavailable (0), -- Vehicle brake pedal detector is unavailable
		off (1), -- Vehicle's brake pedal is not pressed
		on (2) -- Vehicle's brake pedal is pressed
	}
	
	BrakeAppliedStatus ::= BIT STRING {
		unavailable (0), -- When set, the brake applied status is unavailable
		leftFront (1), -- Left Front Active
		leftRear (2), -- Left Rear Active
		rightFront (3), -- Right Front Active
		rightRear (4) -- Right Rear Active
	} (SIZE (5))
	
	BrakeBoostApplied ::= ENUMERATED {
		unavailable (0), -- Vehicle not equipped with brake boost
		-- or brake boost data is unavailable
		off (1), -- Vehicle's brake boost is off
		on (2) -- Vehicle's brake boost is on (applied)
	}
	
	TractionControlStatus ::= ENUMERATED {
		unavailable (0), -- Not Equipped with traction control
		-- or traction control status is unavailable
		off (1), -- traction control is Off
		on (2), -- traction control is On (but not Engaged)
		engaged (3) -- traction control is Engaged
	}
	
	AntiLockBrakeStatus ::= ENUMERATED {
		unavailable (0), -- Vehicle Not Equipped with ABS Brakes
		-- or ABS Brakes status is unavailable
		off (1), -- Vehicle's ABS are Off
		on (2), -- Vehicle's ABS are On ( but not Engaged )
		engaged (3) -- Vehicle's ABS control is Engaged on any wheel
	}
	
	StabilityControlStatus ::= ENUMERATED {
		unavailable (0), -- Not Equipped with SC
		-- or SC status is unavailable
		off (1), -- Off
		on (2), -- On or active (but not engaged)
		engaged (3) -- stability control is Engaged
	}
	
	AuxiliaryBrakeStatus ::= ENUMERATED {
		unavailable (0), -- Vehicle Not Equipped with Aux Brakes
		-- or Aux Brakes status is unavailable
		off (1), -- Vehicle's Aux Brakes are Off
		on (2), -- Vehicle's Aux Brakes are On ( Engaged )
		reserved (3)
	}
	
END

VehClass DEFINITIONS AUTOMATIC TAGS ::= BEGIN

-- imports and exports

EXPORTS VehicleClassification;
IMPORTS ;
	
	VehicleClassification ::= SEQUENCE {
		classification BasicVehicleClass,
		fuelType FuelType OPTIONAL,
		...
	}
	
	--********************************Basic Vehicle Class**************************
	BasicVehicleClass ::= INTEGER (0..255)
	
	unknownVehicleClass BasicVehicleClass ::= 0
	-- Not Equipped, Not known or unavailable
	specialVehicleClass BasicVehicleClass ::= 1
	-- Special use
	--
	-- Basic Passenger Motor Vehicle Types
	--
	passenger-Vehicle-TypeUnknown BasicVehicleClass ::= 10 -- default type
	passenger-Vehicle-TypeOther BasicVehicleClass ::= 11
	-- various fuel types are handled in another element
	--
	-- Light Trucks, Pickup, Van, Panel
	--
	lightTruck-Vehicle-TypeUnknown BasicVehicleClass ::= 20 -- default type
	lightTruck-Vehicle-TypeOther BasicVehicleClass ::= 21
	--
	-- Trucks, Various axle types, includes HPMS items
	--
	truck-Vehicle-TypeUnknown BasicVehicleClass ::= 25 -- default type
	truck-Vehicle-TypeOther BasicVehicleClass ::= 26
	truck-axleCnt2 BasicVehicleClass ::= 27 -- Two axle, six tire single units
	truck-axleCnt3 BasicVehicleClass ::= 28 -- Three axle, single units
	truck-axleCnt4 BasicVehicleClass ::= 29 -- Four or more axle, single unit
	truck-axleCnt4Trailer BasicVehicleClass ::= 30 -- Four or less axle, single trailer
	truck-axleCnt5Trailer BasicVehicleClass ::= 31 -- Five or less axle, single trailer
	truck-axleCnt6Trailer BasicVehicleClass ::= 32 -- Six or more axle, single trailer
	truck-axleCnt5MultiTrailer BasicVehicleClass ::= 33 -- Five or less axle, multi-trailer
	truck-axleCnt6MultiTrailer BasicVehicleClass ::= 34 -- Six axle, multi-trailer
	truck-axleCnt7MultiTrailer BasicVehicleClass ::= 35 -- Seven or more axle, multi-trailer
	--
	-- Motorcycle Types
	--
	motorcycle-TypeUnknown BasicVehicleClass ::= 40 -- default type
	motorcycle-TypeOther BasicVehicleClass ::= 41
	motorcycle-Cruiser-Standard BasicVehicleClass ::= 42
	motorcycle-SportUnclad BasicVehicleClass ::= 43
	motorcycle-SportTouring BasicVehicleClass ::= 44
	motorcycle-SuperSport BasicVehicleClass ::= 45
	motorcycle-Touring BasicVehicleClass ::= 46
	motorcycle-Trike BasicVehicleClass ::= 47
	motorcycle-wPassengers BasicVehicleClass ::= 48 -- type not stated
	--
	-- Transit Types
	--
	transit-TypeUnknown BasicVehicleClass ::= 50 -- default type
	transit-TypeOther BasicVehicleClass ::= 51
	transit-BRT BasicVehicleClass ::= 52
	transit-ExpressBus BasicVehicleClass ::= 53
	transit-LocalBus BasicVehicleClass ::= 54
	transit-SchoolBus BasicVehicleClass ::= 55
	transit-FixedGuideway BasicVehicleClass ::= 56
	transit-Paratransit BasicVehicleClass ::= 57
	transit-Paratransit-Ambulance BasicVehicleClass ::= 58
	--
	-- Emergency Vehicle Types
	--
	emergency-TypeUnknown BasicVehicleClass ::= 60 -- default type
	emergency-TypeOther BasicVehicleClass ::= 61 -- includes federal users
	emergency-Fire-Light-Vehicle BasicVehicleClass ::= 62
	emergency-Fire-Heavy-Vehicle BasicVehicleClass ::= 63
	emergency-Fire-Paramedic-Vehicle BasicVehicleClass ::= 64
	emergency-Fire-Ambulance-Vehicle BasicVehicleClass ::= 65
	emergency-Police-Light-Vehicle BasicVehicleClass ::= 66
	emergency-Police-Heavy-Vehicle BasicVehicleClass ::= 67
	emergency-Other-Responder BasicVehicleClass ::= 68
	emergency-Other-Ambulance BasicVehicleClass ::= 69
	--
	-- Other V2X Equipped Travelers
	--
	otherTraveler-TypeUnknown BasicVehicleClass ::= 80 -- default type
	otherTraveler-TypeOther BasicVehicleClass ::= 81
	otherTraveler-Pedestrian BasicVehicleClass ::= 82
	otherTraveler-Visually-Disabled BasicVehicleClass ::= 83
	otherTraveler-Physically-Disabled BasicVehicleClass ::= 84
	otherTraveler-Bicycle BasicVehicleClass ::= 85
	otherTraveler-Vulnerable-Roadworker BasicVehicleClass ::= 86
	--
	-- Other V2X Equipped Device Types
	--
	infrastructure-TypeUnknown BasicVehicleClass ::= 90 -- default type
	infrastructure-Fixed BasicVehicleClass ::= 91
	infrastructure-Movable BasicVehicleClass ::= 92
	equipped-CargoTrailer BasicVehicleClass ::= 93
	
	--********************************Vehicle Fuel Type**************************
	FuelType ::= INTEGER (0..15)
	
	unknownFuel FuelType::= 0 -- Gasoline Powered
	gasoline FuelType::= 1
	ethanol FuelType::= 2 -- Including blends
	diesel FuelType::= 3 -- All types
	electric FuelType::= 4
	hybrid FuelType::= 5 -- All types
	hydrogen FuelType::= 6
	natGasLiquid FuelType::= 7 -- Liquefied
	natGasComp FuelType::= 8 -- Compressed
	propane FuelType::= 9
	
END

VehEmgExt DEFINITIONS AUTOMATIC TAGS ::= BEGIN

-- imports and exports

EXPORTS VehicleEmergencyExtensions, LightbarInUse;
IMPORTS ;
	
	-- type assignments	
	
	VehicleEmergencyExtensions ::= SEQUENCE {
		responseType ResponseType OPTIONAL,
		sirenUse SirenInUse OPTIONAL,
		lightsUse LightbarInUse OPTIONAL,
		...
	}
	
	ResponseType ::= ENUMERATED {
		notInUseOrNotEquipped (0),
		emergency (1), -- active service call at emergency level
		nonEmergency (2), -- also used when returning from service call
		pursuit (3), -- sender driving may be erratic
		stationary (4), -- sender is not moving, stopped along roadside
		slowMoving (5), -- such a litter trucks, etc.
		stopAndGoMovement (6), -- such as school bus or garbage truck
		...
	}
	
	SirenInUse ::= ENUMERATED {
		unavailable (0), -- Not Equipped or unavailable
		notInUse (1),
		inUse (2),
		reserved (3) -- for future use
	}
	
	LightbarInUse ::= ENUMERATED {
		unavailable (0), -- Not Equipped or unavailable
		notInUse (1), -- none active
		inUse (2),
		yellowCautionLights (3),
		schooldBusLights (4),
		arrowSignsActive (5),
		slowMovingVehicle (6),
		freqStops (7)
	}
	
END

VehSafetyExt DEFINITIONS AUTOMATIC TAGS ::= BEGIN

-- imports and exports

EXPORTS VehicleSafetyExtensions, Confidence, FullPositionVector, GNSSstatus, PathHistory, PathPrediction;
IMPORTS VehicleEventFlags, ExteriorLights, TransmissionState FROM VehStatus
		PositionOffsetLLV FROM DefPositionOffset
		Speed, Heading, MotionConfidenceSet, CoarseHeading FROM DefMotion
		Position3D, PositionConfidenceSet, PositionalAccuracy FROM DefPosition
		DDateTime, TimeOffset, TimeConfidence FROM DefTime;
	
	VehicleSafetyExtensions ::= SEQUENCE {
		events VehicleEventFlags OPTIONAL,
		pathHistory PathHistory OPTIONAL,
		pathPrediction PathPrediction OPTIONAL,
		lights ExteriorLights OPTIONAL,
		...
		}
	
	PathHistory ::= SEQUENCE {
		initialPosition FullPositionVector OPTIONAL,
		currGNSSstatus GNSSstatus OPTIONAL,
		crumbData PathHistoryPointList,
		...
		}
	
	FullPositionVector ::= SEQUENCE {
		utcTime DDateTime OPTIONAL, -- time with mSec precision
		pos Position3D,
		heading Heading OPTIONAL,
		transmission TransmissionState OPTIONAL,
		speed Speed OPTIONAL,
		posAccuracy PositionConfidenceSet OPTIONAL,
		timeConfidence TimeConfidence OPTIONAL,
		motionCfd MotionConfidenceSet OPTIONAL,
		...
		}
	
	GNSSstatus ::= BIT STRING {
		unavailable (0), -- Not Equipped or unavailable
		isHealthy (1),
		isMonitored (2),
		baseStationType (3), -- Set to zero if a moving base station,
		-- or if a rover device (an OBU),
		-- set to one if it is a fixed base station
		aPDOPofUnder5 (4), -- A dilution of precision greater than 5
		inViewOfUnder5 (5), -- Less than 5 satellites in view
		localCorrectionsPresent (6), -- pseudo range corrections used
		networkCorrectionsPresent (7) -- RTK type corrections used
		} (SIZE(8))
		
	PathHistoryPointList ::= SEQUENCE (SIZE(1..23)) OF PathHistoryPoint
	
	PathHistoryPoint ::= SEQUENCE {
		llvOffset PositionOffsetLLV,
		timeOffset TimeOffset,
		-- Offset backwards in time
		speed Speed OPTIONAL,
		-- Speed over the reported period
		posAccuracy PositionConfidenceSet OPTIONAL,
		-- The accuracy of this value
		heading CoarseHeading OPTIONAL,
		-- overall heading
		...
		}
		
	PathPrediction ::= SEQUENCE {
		radiusOfCurve RadiusOfCurvature,
		-- Units of 10cm
		-- straight path to use value of 32767
		confidence Confidence,
		-- Units of 0.5 percent
		...
		}
	
	Confidence ::= INTEGER (0..200) 
	-- Units of 0.5 percent
	
	RadiusOfCurvature ::= INTEGER (-32767..32767) 
	-- Units of 10cm 
	-- A straight path to use value of 32767
	
END

VehSize DEFINITIONS AUTOMATIC TAGS ::= BEGIN

-- imports and exports

EXPORTS VehicleSize;
IMPORTS ;
	
	VehicleSize ::= SEQUENCE {
		width VehicleWidth,
		length VehicleLength,
		height VehicleHeight OPTIONAL
	}
	
	VehicleWidth ::= INTEGER (0..1023) 
	-- Units are 1 cm with a range of >10 meters
	
	VehicleLength ::= INTEGER (0.. 4095)
	-- Units of 1 cm with a range of >40 meters
	
	VehicleHeight ::= INTEGER (0..127)
	-- Units of 5 cm, range to 6.35 meters
	
END

VehStatus DEFINITIONS AUTOMATIC TAGS ::= BEGIN

-- imports and exports

EXPORTS TransmissionState, VehicleEventFlags, ExteriorLights;
IMPORTS ;
	
	TransmissionState ::= ENUMERATED {
		neutral (0), -- Neutral
		park (1), -- Park
		forwardGears (2), -- Forward gears
		reverseGears (3), -- Reverse gears
		reserved1 (4),
		reserved2 (5),
		reserved3 (6),
		unavailable (7)-- not-equipped or unavailable value,
		-- Any related speed is relative to the vehicle reference frame used
	}
	
	VehicleEventFlags ::= BIT STRING {
		eventHazardLights (0),
		eventStopLineViolation (1), -- Intersection Violation
		eventABSactivated (2),
		eventTractionControlLoss (3),
		eventStabilityControlactivated (4),
		eventHazardousMaterials (5),
		eventReserved1 (6),
		eventHardBraking (7),
		eventLightsChanged (8),
		eventWipersChanged (9),
		eventFlatTire (10),
		eventDisabledVehicle (11), -- The DisabledVehicle DF may also be sent
		eventAirBagDeployment (12)
		} (SIZE (13, ...))	
	
	ExteriorLights ::= BIT STRING { 
		-- All lights off is indicated by no bits set
		lowBeamHeadlightsOn (0),
		highBeamHeadlightsOn (1),
		leftTurnSignalOn (2),
		rightTurnSignalOn (3),
		hazardSignalOn (4),
		automaticLightControlOn (5),
		daytimeRunningLightsOn (6),
		fogLightOn (7),
		parkingLightsOn (8)
		} (SIZE (9, ...))
END

VIR DEFINITIONS AUTOMATIC TAGS ::= BEGIN

-- imports and exports

EXPORTS VehIntentionAndRequest, DriveBehavior, PathPlanning;
IMPORTS MsgCount FROM MsgFrame
		DSecond, TimeOffset, DDateTime FROM DefTime
		Position3D, PositionConfidenceSet FROM DefPosition
		NodeReferenceID, LaneID, MovementEx FROM Map
		PositionOffsetLLV FROM DefPositionOffset
		ReferencePathList, ReferenceLink, ReferencePath FROM RSI
		Speed, Heading, SpeedConfidence, HeadingConfidence FROM DefMotion
		Confidence FROM VehSafetyExt
		VehicleClassification FROM VehClass
		ParkingType FROM PAM
		AccelerationSet4Way FROM DefAcceleration
		AccSet4WayConfidence FROM SensorSharing;
	
	VehIntentionAndRequest ::= SEQUENCE {
		msgCnt MsgCount,
		id OCTET STRING (SIZE(8)),
		-- temperary vehicle ID
		-- same as id in BSM
		secMark DSecond,
		refPos Position3D,
		-- vehicle real position relates to secMark
		intAndReq IARData,
		-- vehicle intention and request
		...
	}
	
	IARData ::= SEQUENCE {
		currentPos PathPlanningPoint OPTIONAL,
		-- current position in MAP
		path-Planning PathPlanning OPTIONAL,
		-- real time path planning that is shared with neighbors
		-- list in chronological order
		currentBehavior DriveBehavior OPTIONAL,
		-- drive behavior related to the path planning
		reqs SEQUENCE (SIZE(1..8)) OF DriveRequest OPTIONAL,
		...
	}
	
	PathPlanning ::= SEQUENCE (SIZE(1..100)) OF PathPlanningPoint
	-- 考虑8s规划，1s用10个点表示，共需80个点。预留到100个
	
	PathPlanningPoint ::= SEQUENCE {
		posInMap ReferenceLink OPTIONAL,
		-- Lane and Link location related to MAP
		pos PositionOffsetLLV,
		-- Target location in the path
		posAccuracy PositionConfidenceSet OPTIONAL,
		speed Speed OPTIONAL,
		-- Target speed or recommended speed when passing the target position
		speedCfd SpeedConfidence OPTIONAL,
		-- Considering the acceptable range of the above target speed
		heading Heading OPTIONAL,
		headingCfd HeadingConfidence OPTIONAL,
		accelSet AccelerationSet4Way OPTIONAL,
		acc4WayConfidence AccSet4WayConfidence OPTIONAL,
		estimatedTime TimeOffset OPTIONAL,
		-- Estimated time when vehicle reaches the target position
		-- Time offset is calculated from secMark of this message
		timeConfidence Confidence OPTIONAL,
		-- Considering the acceptable range of the above estimated time
		...
	}
	
	DriveBehavior ::= BIT STRING {
		goStraightForward(0),
		laneChangingToLeft(1),
		laneChangingToRight(2),
		rampIn(3),
		rampOut(4),
		intersectionStraightThrough(5),
		intersectionTurnLeft(6),
		intersectionTurnRight(7),
		intersectionUTurn(8),
		stop-and-go(9),
		stop(10),
		slow-down(11),
		speed-up(12),
		parking(13)
	} (SIZE(14,...))
	
	DriveRequest ::= SEQUENCE {
		reqID INTEGER (0..255),
		-- local ID of this request
		-- same request in serial VIR messages should keep the same reqID
		status ReqStatus,
		reqPriority OCTET STRING (SIZE(1)) OPTIONAL,
		-- The lower five bits are reserved and shall be set to zero
		-- Value from B00000000 to B11100000 represents the lowest to the highest level
		targetVeh OCTET STRING (SIZE(8)) OPTIONAL,
		-- the temporary ID of target vehicle
		targetRSU OCTET STRING (SIZE(8)) OPTIONAL,
		-- the temporary ID of target RSU
		info ReqInfo OPTIONAL,
		lifeTime TimeOffset OPTIONAL,
		-- Lifetime of this request
		-- Time offset is calculated from secMark of this message
		...
	}
	
	ReqInfo ::= CHOICE {
		laneChange Req-LaneChange,
		clearTheWay Req-ClearTheWay,
		signalPriority Req-SignalPriority,
		sensorSharing Req-SensorSharing,
		parking Req-ParkingArea,
		...
	}
	
	ReqStatus ::= ENUMERATED {
		unknown(0),
		request(1),
		-- raise the request and not comfirmed by the target devices yet
		comfirmed(2),
		-- this request is already comfirmed through some methods
		cancel(3),
		-- vehicle claims to cancel this request
		complete(4),
		-- vehicle has just completed this driving behavior
		...
	}
	
	Req-LaneChange ::= SEQUENCE {
		upstreamNode NodeReferenceID,
		-- Upstream node of the target link
		downstreamNode NodeReferenceID,
		-- Downstream node of the target link
		targetLane LaneID,
		-- Target lane to change to
		...
	}
	
	Req-ClearTheWay ::= SEQUENCE {
		upstreamNode NodeReferenceID,
		downstreamNode NodeReferenceID,
		targetLane LaneID,
		-- Target lane to clear the way
		relatedPath ReferencePath OPTIONAL,
		-- Describe the detailed road area to clear
		tBegin DDateTime OPTIONAL,
		-- The beginning time required to clearing the way
		tEnd DDateTime OPTIONAL,
		-- The time to end clearing the way
		...
	}
	
	Req-SignalPriority ::= SEQUENCE {
		intersectionId NodeReferenceID,
		-- Intersection id indicating the target traffic signal
		requiredMov MovementEx,
		-- Movement info. required including remote intersection id, target phase id and turning direction
		estimatedArrivalTime TimeOffset OPTIONAL,
		-- Estimated arrival time to the intersection
		distance2Intersection INTEGER (0..10000) OPTIONAL,
		-- Unit 0.1m
		...
	}
	
	Req-SensorSharing ::= SEQUENCE {
		detectArea ReferencePathList,
		...
	}
	
	ParkingRequest ::=  BIT STRING {
		enter(0),
		exit(1),
		park(2),
		pay(3),
		unloadPassenger(4),
		pickupPassenger(5),
		unloadCargo(6),
		loadCargo(7),
		reserved1(8),
		reverved2(9),
		reserved3(10),
		reverved4(11)
	}(SIZE(12,...))
	
	Req-ParkingArea ::= SEQUENCE {
		vehicleClass VehicleClassification,
		req ParkingRequest,
		-- request from this vehicle for the parking area
		-- or traffic station 
		
		parkingType ParkingType OPTIONAL,
		-- if the vehicle needs a parking slot of certain type
		expectedParkingSlotID INTEGER (0..65535) OPTIONAL,
		-- if the vehicle already has a target parking slot
		...
	}
	
END

VPM DEFINITIONS AUTOMATIC TAGS ::= BEGIN

-- imports and exports

EXPORTS VehiclePaymentMessage;
IMPORTS MsgCount FROM MsgFrame
		Position3D FROM DefPosition
		NodeReferenceID FROM Map
		PositionOffsetLLV FROM DefPositionOffset
		DYear, DMonth, DDay, DDateTime FROM DefTime
		ReferencePath FROM RSI
		Speed, Heading FROM DefMotion;
	
	VehiclePaymentMessage::= SEQUENCE{
		msgCnt MsgCount,
	
		payment CHOICE{
			initialzation-request    	RST,
			--Roadside Service Talbe
			initialzation-response   	VSI,
			--Vehicle Service Indication
			action-request 				Action-Request,
			action-response				Action-Response,
			...
		},
		...
	}
	
	RST::= SEQUENCE{
		time 				DDateTime,								
		id 					OCTET STRING (SIZE(8)),				
		-- RSU Id
		paymentList 		PaymentList,						
		-- Payment/service list
		...
	}

	PaymentList ::= SEQUENCE(SIZE(1..16)) OF ApplicationParameter

	ApplicationParameter::=SEQUENCE{
		pid 			PaymentEntityID,
		-- Payment type of road toll or services
		paymentInfo		PaymentInfo,
		-- Payment detailed information
		
		...															
	}
	
	PaymentInfo::=CHOICE{
		paymentInfoType1	PaymentInfoType1,
		-- other types of payment info.
		-- can be extended in the future
		...
	}
	
	PaymentEntityID::=ENUMERATED{
		system(0),			-- reserved
		freeflow(1), 		-- free flow toll
		enclosed(2),		-- enclosed road toll
		congestion(3),		-- Congestion fee
		charging(4),		-- Charging fee
		parking(5),			-- Parking fee
		...
	}
	
	PaymentInfoType1::=SEQUENCE{
		tollingNodeInfo		TollingNodeInfo OPTIONAL,
		tollInfo			TollInfo OPTIONAL,
		serviceInfo			OCTET STRING (SIZE(1..512)) OPTIONAL,		
		-- Reserved for more payment sevices
		...
	}

	TollingNodeInfo::=SEQUENCE{
		id					StationOrGantryId OPTIONAL,	
		-- Tolling Station or Tolling Gantry Id
		pos					Position3D OPTIONAL,
		tollingNodeType		TollingNodeType OPTIONAL,
		tollingDirection	TollingDirection OPTIONAL,
		...
	}
	
	StationOrGantryId ::= INTEGER (0..4294967295,...)
	
	TollingNodeType::=ENUMERATED{
		entranceStation(0),
		exitStation(1),
		entranceAndExitStation(2),
		gantry(3),
		...
	}
	
	TollingDirection::=ENUMERATED{
		north(0),
		northeast(1),
		east(2),
		southeast(3),
		south(4),
		southwest(5),
		west(6),
		northwest(7),
		...
	}
	
	TollInfo::=SEQUENCE{
		price				INTEGER(0..424967295) OPTIONAL,			
		-- Estimated price, value 1 = ￥0.01
		entrancePos 		PositionOffsetLLV OPTIONAL,				
		-- Entrance of the toll road
		exitPos				PositionOffsetLLV OPTIONAL,		
		-- Exit of the toll road
		tollRoad 			SEQUENCE (SIZE(2..256)) OF NodeReferenceID OPTIONAL,
		-- Toll road represented by a list of node id sorted from upstream to downstream
		tollPath				ReferencePath OPTIONAL,
		-- Toll path represented by a point list from upstream to downstream
		timeBegin 			DDateTime OPTIONAL,							
		-- Beginning of charging time
		timeEnd 			DDateTime OPTIONAL,							
		-- End of charging time
		...
	}
	
	VSI::=SEQUENCE{
		time				DDateTime,
		obuId 				OCTET STRING (SIZE(8)),					
		-- Host OBU Id
		targetId 		OCTET STRING (SIZE(8))	OPTIONAL,			
		-- Target RSU Id, necessary in broadcast mode
		obuInfo				OBUInfo OPTIONAL,
		vpapplicationList	VPApplicationList OPTIONAL,
		rndOBU				RandStr8 OPTIONAL, 
		--CON ETC SEC Mode	
		-- Rand string of length(8) from ESAM
		...
	}
	
	VPApplicationList::=SEQUENCE (SIZE(1..16)) OF VPApplicationParameter

	VPApplicationParameter::=SEQUENCE{
		pid 				PaymentEntityID,
		obuPaymentInfo		OBUPaymentInfo,
		...
	}
	
	OBUPaymentInfo::=CHOICE{
		obuPaymentInfoType1	OBUPaymentInfoType1,
		...
	}

	OBUPaymentInfoType1::=SEQUENCE{
		equipmentClass EquipmentClass OPTIONAL,
		--支付设备类型
		gbiCCInfo GBICCInfo	OPTIONAL,
		--IC卡预读信息
		sysInfo SysInfo OPTIONAL,
		--系统信息文件
		vehicleInfo VehicleInfo OPTIONAL,
		passedSitesInfo PassedSitesInfo OPTIONAL,
		...
	}
	
	EquipmentClass::= ENUMERATED{
		onechipOBU	(0),
		--单片式
		iccOBU		(1),
		--双片式
		cpcOBU		(2),
		--CPC卡
		...
	}

	GBICCInfo ::= SEQUENCE{
		iccIssueInfo	OCTET STRING(SIZE(0..127,...)),		
		--卡片发行节本信息
		iccUniTollInfo	OCTET STRING(SIZE(0..127,...)),
		--联网典型收费信息
		iccBalance		OCTET STRING(SIZE(0..127,...)),
		--电子钱包余额
		...
	}

	OBUInfo::=SEQUENCE{
		obuType				OBUType,
		obuMotionStatus		OBUMotionStatus OPTIONAL,
		...
	}

	OBUType::=ENUMERATED{
		oemObu(0),
		aftermarketObu(1),
		mobilePhone(2),
		...
	}
	
	OBUMotionStatus::=SEQUENCE{
		pos					Position3D OPTIONAL,
		heading				Heading OPTIONAL,
		speed				Speed OPTIONAL,
		...
	}
	
	RandStr8 ::= OCTET STRING(SIZE(8))
	
	SysInfo::=SEQUENCE{
		contractProvider		OCTET STRING(SIZE(8)),
		contractType			INTEGER(0..127,...),
		contractVersion			INTEGER(0..127,...),
		contractSerialNumer		OCTET STRING(SIZE(8)),
		contractSignedDate		Date,
		contractExpiredDate		Date,
		reserved				OCTET STRING(SIZE(64)),
		...
	}
	
	VehicleInfo ::= SEQUENCE {
        vehicleLicencePlateNumber OCTET STRING(SIZE(12)),
        --车牌号码，全牌照（汉字+字母+数字）信息，汉字采用GB/T 2312编码，字母数字采用ASCII编码
        vehicleLicencePlateColor OCTET STRING(SIZE(2)),
        --车牌颜色，二进制编码表示。0-蓝色，1-黄色，2-黑色，3-白色，4-小型新能源汽车号牌颜色，5-大型新能源汽车号牌颜色
        vehicleTollingClass INTEGER(0..127,...),
        --车辆计费类型。1-一型客车，2-二型客车，3-三型客车，4-四型客车，5-五型客车，6-六型客车，
        --            11-一型货车，12-二型货车，13-三型货车，14-四型货车，15-五型货车，16-六型货车
        vehicleUserType INTEGER (0..127,...),
        --车辆用户类型。0-普通车，6-公务车，8-军警车，10-紧急车，12-免费，14-车队
        vehicleDimensions VehicleDimensions,
        --车辆尺寸，长宽高，单位分米。
        vehicleWheels INTEGER (0..127),
        --车轮数
        vehicleAxles INTEGER (0..127),
        --车轴数
        vehicleWheelBases INTEGER (0..65535),
        --轴距，单位分米
        vehicleWeightLimits INTEGER (0..16777215),
        --车辆载重（货车）或座位数（客车），单位为kg（货车）或座（客车）
        vehicleSpecificInformation OCTET STRING(SIZE(16)),
        --车辆特征描述，字符用ASCII编码表示，汉字用机内码表示，如“某品牌307”
        vehicleEngineNumber OCTET STRING(SIZE(16)),
        --车辆发动机号
        
        description OCTET STRING (SIZE(1..256)) OPTIONAL,
        -- Other information description of the vehicle
        ...
    }
	
	VehicleDimensions::=SEQUENCE{
        vehicleLength		INTEGER(0..65535),
        vehicleWidth		INTEGER(0..255),
        vehicleHeigth		INTEGER(0..255),
        ...
    }

	TollingPos ::= SEQUENCE{
        id 					StationOrGantryId,
        --收费站或门架编号
        pos 				Position3D OPTIONAL,
        --收费站或门架位置
        ...
    }
	
    PassedPos::= SEQUENCE{
		tollingPos			TollingPos,
        --经过的收费站/门架信息
        tollingTime			DDateTime,
        --经过收费站/门架时的时间
        tollingAmount		OCTET STRING(SIZE(4)) OPTIONAL,		
		--收费金额
        ...
    }

    PassedSitesInfo::=SEQUENCE{
        entranceInfo PassedPos OPTIONAL,
        --进场（比如进入高速）信息
        passedPos SEQUENCE (SIZE(2..512)) OF PassedPos OPTIONAL,
        --过站（比如经过收费门架）信息
        ...
    }
	
	Date ::= SEQUENCE {
		year DYear,
		month DMonth,
		day DDay
	}
	
	Action-Request::=SEQUENCE{
		time				DDateTime,
		mode				BOOLEAN,		
		-- Mode 1 needs confirm; Mode 0 needs not
		sourceId			OCTET STRING (SIZE(8)),
		-- Rsu ID
		targetId 			OCTET STRING (SIZE(8))	OPTIONAL,		
		-- Target OBU ID,  necessary in broadcast mode
		paymentEntityId		PaymentEntityID,
		actionParameter		TransInfo,
		accessCredentials	OCTET STRING (SIZE(8)) OPTIONAL,
		--CON ETC SEC Mode
		-- RSU's certification to visit OBU, calculated from rndOBU in VSI
		...
	}
		
	Action-Response::=SEQUENCE{
		time				DDateTime,
		sourceId 			OCTET STRING (SIZE(8)),					
		-- Host OBU Id
		targetId 			OCTET STRING (SIZE(8))	OPTIONAL,		
		-- Target RSU Id, necessary in broadcast mode
		paymentEntityId		PaymentEntityID,
		responseParameter	TransInfo OPTIONAL,	
		ret 				ReturnStatus,
		...
	}
	
	ReturnStatus::=ENUMERATED{
		noError				(0),						
		--请求的操作执行成功		
		accessDenied		(1),						
		--请求操作未执行（安全原因）
		argumnetError		(2),						
		--文件内容访问失败
		complexityLimitation(3),						
		--请求操作参数复杂而未执行
		processingFailure	(4),						
		--操作要一般性失败
		processing			(5),						
		--操作正在处理但结果不能用
		...
	}
	
	TransInfo::= CHOICE{
		getTollDataRq 	GetTollDataRq,					
		--单片式请求获取收费数据、车辆信息
		getTollDataRs	GetTollDataRs,					
		--单片式响应收费数据、车辆信息

		getSecureRq		GetSecureRq,
		--双片式请求获取车辆信息
		getSecureRs		GetSecureRs,
		--双片式响应车辆信息

		setTollDataRq 	SetTollDataRq,					
		--请求写入通信凭证和入口信息
		setTollDataRs 	SetTollDataRs,					
		--响应写入通信凭证和入口信息操作

		transferChannelRq	ChannelRq,
		--请求向OBU内模块发送操作指令
		transferChannelRs	ChannelRs,
		--操作指令结果响应
		
		setMMIRq 		SetMMIRq,						
		--用户提示
		...
	}
	
	GetTollDataRq::=SEQUENCE{
		vehicleInfo			RangeOfFile,
		--文件系统中取车辆信息
		tollInfo			RangeOfFile OPTIONAL,
		--文件系统中取出入口信息
		keyIdForAC			INTEGER(0..255) OPTIONAL,
		--秘钥标识，指示OBU选择相应秘钥进行访问许可认证
		...
	}

	
	GetTollDataRs::=SEQUENCE{
		vehicleInfo			File,
		--车辆信息文件内容
		tollInfo			File OPTIONAL,
		--出入口信息文件内容
		...
	}
	
	RangeOfFile::=SEQUENCE{
		offset			INTEGER(0..32767),
		--文件实际偏移量
		length			INTEGER(0..127)
		--信息长度
	}
		
	File ::= OCTET STRING(SIZE(127))
	
	PartOfFile::=SEQUENCE{
		offset			INTEGER(0..32767),
		--文件实际偏移量
		length			INTEGER(0..127),
		--信息长度
		fileContent		File
		--信息内容
	}
	
	GetSecureRq ::= SEQUENCE{
		vehicleInfo			RangeOfFile,
		--文件系统中取车辆信息
		rndRsuForAuthen		RandStr8,
		--8字节随机数
		keyIdForAuthen		INTEGER(0..255),
		--指示信息鉴别秘钥的秘钥标识
		keyIdForEncrypt		INTEGER(0..255) OPTIONAL,
		--指示加密秘钥的版本秘钥标识,不选取表示不对数据加密
		...
	}

	GetSecureRs ::= SEQUENCE{
		file			RangeOfFile,
		--车辆信息文件
		authenticator	OCTET STRING (SIZE(8)),
		--RSU对OBU进行认证的信息鉴别码
		...
	}
		
	SetTollDataRq::=SEQUENCE{
		rndRSU				RandStr8 OPTIONAL,
		-- 获取PSAM 8字节随机数
		-- Mandatory in ETC Security Mode
		transPara			TransPara OPTIONAL,
		--交易记录，存于DF01/EF04
		tollInfo			PartOfFile OPTIONAL,	--CON ETC SEC Mode
		--出入站信息
		tollingPos 			TollingPos OPTIONAL,
		--当前收费站/门架信息
		keyIdForAuthen		INTEGER(0..255) OPTIONAL,	--CON ETC SEC Mode
		--秘钥版本，指示OBU选择相应的秘钥进行信息鉴别
		...
	}
	
	TransPara::=SEQUENCE{
		transAmount			OCTET STRING(SIZE(4)),		
		--通行费额
		transType			OCTET STRING(SIZE(1)),		
		--交易类型
		terminalID			OCTET STRING(SIZE(6)),		
		--终端编号
		transSN				OCTET STRING(SIZE(4)),		
		--交易序号	
		transTime			OCTET STRING(SIZE(7)),		
		--通行时间
		transStationID		OCTET STRING(SIZE(3))		
		--门架/收费站编号	
	}
		
	SetTollDataRs::=SEQUENCE{
		tacInfo				OCTET STRING (SIZE(4)) OPTIONAL,	--CON ETC SEC Mode
		--TAC码
		authenticator		OCTET STRING (SIZE(8)) OPTIONAL,	--CON ETC SEC Mode
		--鉴别报文
		
		accountInfo			AccountInfo OPTIONAL,		--CON LTE-V SEC Mode
		transCredential		TransCredential OPTIONAL,	--CON LTE-V SEC Mode
		...
	}
		
	SetMMIRq ::= SEQUENCE{
        toll TollResult,
        ...
	}
	
	TollResult ::= ENUMERATED{
		ok(0),
		--正常交易
		nok(1),
		--交易异常（通信、设备故障）
		contactOperator(2)
		--联系运营商（过期、黑名单）				
	}
	
	AccountInfo ::= SEQUENCE{
        account OCTET STRING (SIZE(2..32)),
        --账号
        ...
    }
	
	TransCredential ::= SEQUENCE {
		tc OCTET STRING (SIZE (32, ...)) ,
		...
	}

	ChannelRq ::= SEQUENCE{
		channelid		ChannelID,
		--通道标识ID
		apdu			ApduList,
		--通道指令数据
		...
	}

	ChannelRs ::= SEQUENCE{
		channelid		ChannelID,
		--通道标识ID
		apdu			ApduList,
		--通道应答数据
		...
	}

	ChannelID ::= ENUMERATED{
		obu			(0),
		esam		(1),
		icc			(2),
		hmi			(3),
		beeper		(4)
	}

	ApduList ::= SEQUENCE OF OCTET STRING(SIZE(127))
		
END
